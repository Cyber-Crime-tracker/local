(DEFUN C:BOQF()
  (command "line" "0,0" "0,0" "")
  (setq sri(entlast))
  (command "lengthen" sri "" "" "")
  (command "erase" sri "")
  (setq a(ssget (list (cons 0 "lwpolyline"))))
  (setq sl(sslength a))
  (setq num 0)
  (setq la 0)
  (setq lb 0)
  (setq lc 0)
  (setq ld 0)
  (setq le 0)
  (setq lf 0)
  (setq lg 0)
  (setq lh 0)
  (setq li 0)
  (setq la1 0)
  (setq lb1 0)
  (setq lc1 0)
  (setq ld1 0)
  (setq le1 0)
  (setq lf1 0)
  (setq lg1 0)
  (setq lh1 0)
  (setq li1 0)
  (repeat sl
    (setq an(ssname a num))
    (COMMAND "LENGTHEN" an "" "" "")
    (SETQ len(GETVAR "PERIMETER"))
    (setq b(cdr(assoc 62 (entget an))))
    (if(= b 224)(setq la1(+ la len)))
    (if(= b 145i
rt
i
)(setq lb1(+ lb len)))
    (if(= b 30)(setq lc1(+ lc len)))
    (if(= b 149)(setq ld1(+ ld len)))
    (if(= b 5)(setq le1(+ le len)))
    (if(= b 200)(setq lf1(+ lf len)))
    (if(= b 32)(setq lg1(+ lg len)))
    (if(= b 11)(setq lh1(+ lh len)))
    (if(= b 4)(setq li1(+ li len)))
    (setq la la1)
    (setq lb lb1)
    (setq lc lc1)
    (setq ld ld1)
    (setq le le1)
    (setq lf lf1)
    (setq lg lg1)
    (setq lh lh1)
    (setq li li1)
    (setq num(+ num 1))
    )
  (setq fla(strcat "\nTotal Length of 1600 Pair Cable =" " "
		   (rtos la1 2 2)))
  (setq flb(strcat "\nTotal Length of Transport Pair Cable =" " "
		   (rtos lb1 2 2)))
  (setq flc(strcat "\nTotal Length of 96F-Ring2 Pair Cable =" " "
		   (rtos lc1 2 2)))
  (setq fld(strcat "\nTotal Length of 96F-Ring1 Pair Cable =" " "
		   (rtos ld1 2 2)))
  (setq fle(strcat "\nTotal Length of 96F Pair Cable =" " "
		   (rtos le1 2 2)))
  (setq flf(strcat "\nTotal Length of 48F Pair Cable =" " "
		   (rtos lf1 2 2)))
  (setq flg(strcat "\nTotal Length of 24F Pair Cable =" " "
		   (rtos lg1 2 2)))
  (setq flh(strcat "\nTotal Length of 12F Pair Cable =" " "
		   (rtos lh1 2 2)))
  (setq fli(strcat "\nTotal Length of 10 Pair Cable =" " "
		   (rtos li1 2 2)))
  (princ fla)(princ)
  (princ flb)(princ)
  (princ flc)(princ)
  (princ fld)(princ)
  (princ fle)(princ)
  (princ flf)(princ)
  (princ flg)(princ)
  (princ flh)(princ)
  (princ fli)(princ)
  )

(DEFUN C:DPF()
  (SETQ A(strcase(GETSTRING "1/2/3/4: ")))
  (WHILE (= A "1")
    (setq a(car(entsel "Pick block to change: ")))
    (setq b(entget a))
    (setq ed (subst (cons 2 "24F-Pole") (assoc 2 b) b ))
    (entmod ed)
  )
  (WHILE (= A "2")
    (setq a(car(entsel "Pick block to change: ")))
    (setq b(entget a))
    (setq ed (subst (cons 2 "32F-Pole") (assoc 2 b) b ))
    (entmod ed)
  )
  (WHILE (= A "3")
    (setq a(car(entsel "Pick block to change: ")))
    (setq b(entget a))
    (setq ed (subst (cons 2 "24F-DP") (assoc 2 b) b ))
    (entmod ed)
  )
  (WHILE (= A "4")
    (setq a(car(entsel "Pick block to change: ")))
    (setq b(entget a))
    (setq ed (subst (cons 2 "32F-DP") (assoc 2 b) b ))
    (entmod ed)
  )
)


(defun c:PFT()
  (princ "Make Cabtxt block")(princ)
(defun rt()
  (setq os(getvar "osmode"))
  (setvar "osmode" 512)
  (setq a1(getpoint "Pick Nearby End point: "))
  (setq b(getpoint a1 "Pick Nearby End point: "))
  (setq c(angle a1 b))
  (setq d(car(entsel "Pick Text to Align: ")))
  (while (= d nil)
      (setq d(car(entsel "Pick Text to Align: ")))
  )
  (setq e(entget d))
  (setq f(cdr(assoc 50 e)))
  (setq ed(subst (cons 50 c) (assoc 50 e) e))
  (entmod ed)
  (setvar "osmode" os)
)
  (command "line" "0,0" "0,0" "")
  (setq eta(entlast))
  (command "lengthen" eta "" "" "")
  (command "erase" eta "")
  (Setq ent(car(entsel "Pick Cable: ")))
  (setq a(cdr(assoc 62(entget ent))))
  (SETQ cl "XXX")
  (COND  ((= a 4)(SETQ cl "10"))
	 ((= a 11)(SETQ cl "20"))
	 ((= a 32)(SETQ cl "24F"))
	 ((= a 200)(SETQ cl "48F"))
	 ((= a 5)(SETQ cl "200"))
	 ((= a 149)(SETQ cl "96F"))
 	 ((= a 30)(SETQ cl "96F"))
	 ((= a 145)(SETQ cl "1200"))
	 ((= a 224)(SETQ cl "1600"))
  )
  (setq os(getvar "osmode"))
  (setvar "osmode" 16385)
  (COMMAND "INSERT" "cabtxt" PAUSE "" "" "0")
  (SETQ cb(ENTLAST))
  (COMMAND "EXPLODE" cb "")
  (SETQ cb1(ENTLAST))
  (setq os(getvar "osmode"))
  (setvar "osmode" 512)
  (setq art(getpoint "Pick Nearby End point: "))
  (setq brt(getpoint art "Pick Nearby End point: "))
  (setq crt(angle art brt))
  (setq ert(entget cb1))
  (setq frt(cdr(assoc 50 ert)))
  (setq ed2(subst (cons 50 crt) (assoc 50 ert) ert))
  (entmod ed2)
  (setvar "osmode" os)
  (SETQ cb2(ENTGET cb1))
  (setq l "")
  (COMMAND "LENGTHEN" ent "" "" "")
  (SETQ VL(GETVAR "PERIMETER"))
  (setq l1(rtos vl 2 0))
  (SETQ SL1(STRLEN L1))
  (SETQ SL(STRLEN L))
  (IF (= SL 0)
    (setq ft cl)
    (setq ft(strcat cl "(" l ")"))
  )
  (IF (= SL1 0)
    (setq ft FT)
    (setq ft(strcat ft "/" l1))
  )
  (setq ed(subst (cons 1 FT)(assoc 1 cb2) cb2))
  (entmod ed)
  )
