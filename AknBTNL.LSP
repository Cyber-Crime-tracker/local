;==============================================================================
;Following programs are to change text of Pillar and sub Pillars               
;==============================================================================
(DEFUN C:CPT()
  (SETQ OT(GETSTRING "\nEnter OLD TEXT: "))
  (SETQ NT(GETSTRING "\nEnter NEW TEXT: "))
  (setq di(getint "\nEnter digit number: "))
  (SETQ TT1(STRCAT OT "*"))
  (SETQ A(SSGET "X"(LIST (CONS 1 TT1))))
  (SETQ B(SSLENGTH A))
  (SETQ NUM 0)    
  (REPEAT B
    (SETQ ON(SSNAME A NUM))
    (SETQ ON1(ENTGET ON))
    (SETQ ONT(CDR(ASSOC 1 ON1)))
    (SETQ NU(SUBSTR ONT di))
    (SETQ NN(STRCAT NT NU))
    (setq ed (subst (cons 1 nn) (assoc 1 on1) on1 ))
    (entmod ed)
    (setq num (+ num 1))
  )
)
(DEFUN C:CT1()
  (SETQ OT(GETSTRING "\nEnter OLD TEXT: "))
  (SETQ NT(GETSTRING "\nEnter NEW TEXT: "))
  (setq di(getint "\nEnter digit number: "))
  (SETQ TT1(STRCAT OT "*"))
  (SETQ A(SSGET (LIST (CONS 1 TT1))))
  (SETQ B(SSLENGTH A))
  (SETQ NUM 0)
  (REPEAT B
    (SETQ ON(SSNAME A NUM))
    (SETQ ON1(ENTGET ON))
    (SETQ ONT(CDR(ASSOC 1 ON1)))
    (SETQ NU(SUBSTR ONT di))
    (SETQ NN(STRCAT NT NU))
    (setq ed (subst (cons 1 nn) (assoc 1 on1) on1 ))
    (entmod ed)
    (setq num (+ num 1))
  )
)
(DEFUN C:chn()
  (SETQ NNUM(GETSTRING "\nEnter NEW NUMBER: "))
  (SETQ TT(GETSTRING "\nEnter ABR: "))
  (SETQ FT(STRCAT TT "*"))
  (SETQ A(SSGET "X"(LIST (CONS 0 "TEXT") (CONS 1 FT))))
  (SETQ B(SSLENGTH A))
  (SETQ NUM 0)
  (REPEAT B
    (SETQ ON(SSNAME A NUM))
    (SETQ ON1(ENTGET ON))
    (SETQ ONT(CDR(ASSOC 1 ON1)))
    (SETQ PN(SUBSTR ONT 1 3))
    (SETQ PN1(SUBSTR ONT 6))
    (setq nn(strcat pn NNUM pn1))
    (setq ed (subst (cons 1 nn) (assoc 1 on1) on1 ))
    (entmod ed)
    (setq num (+ num 1))
  )
)
(DEFUN C:PN()
  (SETQ NNUM(GETSTRING "\nEnter NEW NUMBER: "))
  (SETQ TT(GETSTRING "\nEnter ABR: "))
  (SETQ FT(STRCAT TT "*"))
  (SETQ A(SSGET (LIST (CONS 0 "TEXT") (CONS 1 FT))))
  (SETQ B(SSLENGTH A))
  (SETQ NUM 0)
  (REPEAT B
    (SETQ ON(SSNAME A NUM))
    (SETQ ON1(ENTGET ON))
    (SETQ ONT(CDR(ASSOC 1 ON1)))
    (SETQ PN(SUBSTR ONT 1 3))
    (SETQ PN1(SUBSTR ONT 6))
    (setq nn(strcat pn NNUM pn1))
    (setq ed (subst (cons 1 nn) (assoc 1 on1) on1 ))
    (entmod ed)
    (setq num (+ num 1))
  )
)
(DEFUN C:PN1()
  (SETQ NNUM(GETSTRING "\nEnter ABR Mr.Roopesh: "))
  (SETQ A(SSGET (LIST (CONS 8 "TEXT"))))
  (SETQ B(SSLENGTH A))
  (SETQ NUM 0)
  (REPEAT B
    (SETQ ON(SSNAME A NUM))
    (SETQ ON1(ENTGET ON))
    (SETQ ONT(CDR(ASSOC 1 ON1)))
    (setq nn(strcat NNUM ont))
    (setq ed (subst (cons 1 nn) (assoc 1 on1) on1 ))
    (entmod ed)
    (setq num (+ num 1))
  )
)
;==============================================================================
;Following programs are to change colours of cables
;==============================================================================
(DEFUN C:Ccc()
  (SETQ A(GETSTRING "1/2/5/10/20/40/80/12/16: "))
  (WHILE (= A "1")
    (SETQ A(SSGET))
    (command "change" a "" "p" "c" 4 "")
  )
  (WHILE (= A "2")
    (SETQ A(ssget))
    (command "change" a "" "p" "c" 11 "")
  )
  (WHILE (= A "5")
    (SETQ A(ssget))
    (command "change" a "" "p" "c" 32 "")
  )
  (WHILE (= A "10")
    (SETQ A(ssget))
    (command "change" a "" "p" "c" 200 "")
  )
  (WHILE (= A "20")
    (SETQ A(ssget))
    (command "change" a "" "p" "c" 5 "")
  )
  (WHILE (= A "40")
    (SETQ A(ssget))
    (command "change" a "" "p" "c" 149 "")
  )
  (WHILE (= A "80")
    (SETQ A(ssget))
    (command "change" a "" "p" "c" 30 "")
  )
  (WHILE (= A "12")
    (SETQ A(ssget))
    (command "change" a "" "p" "c" 145 "")
  )
  (WHILE (= A "16")
    (SETQ A(ssget))
    (command "change" a "" "p" "c" 224 "")
  )
)
;==============================================================================
;Following programs are to change text and blocks of "Dps"
;==============================================================================
(DEFUN C:DP()
  (SETQ A(strcase(GETSTRING "1/2/3/4/5/6/7/8/9/10/20/Q1/Q2: ")))
  (WHILE (= A "1")
    (SETQ A(CAR(ENTSEL "Pick TEXT TO CHANGE : ")))
    (SETQ B(ENTGET  A))
    (SETQ C "10")
    (setq ed (subst (cons 1 C) (assoc 1 b) b ))
    (entmod ed)
    (setq a(car(entsel "Pick block to change: ")))
    (setq b(entget a))
    (setq ed (subst (cons 2 "24F-Pole") (assoc 2 b) b ))
    (entmod ed)
  )
  (WHILE (= A "2")
    (SETQ A(CAR(ENTSEL "Pick TEXT TO CHANGE : ")))
    (SETQ B(ENTGET  A))
    (SETQ C "20")
    (setq ed (subst (cons 1 C) (assoc 1 b) b ))
    (entmod ed)
    (setq a(car(entsel "Pick block to change: ")))
    (setq b(entget a))
    (setq ed (subst (cons 2 "32F-Pole") (assoc 2 b) b ))
    (entmod ed)
  )
  (WHILE (= A "3")
    (SETQ A(CAR(ENTSEL "Pick TEXT TO CHANGE : ")))
    (SETQ B(ENTGET  A))
    (SETQ C "30")
    (setq ed (subst (cons 1 C) (assoc 1 b) b ))
    (entmod ed)
    (setq a(car(entsel "Pick block to change: ")))
    (setq b(entget a))
    (setq ed (subst (cons 2 "24F-DP") (assoc 2 b) b ))
    (entmod ed)
  )
  (WHILE (= A "4")
    (SETQ A(CAR(ENTSEL "Pick TEXT TO CHANGE : ")))
    (SETQ B(ENTGET  A))
    (SETQ C "40")
    (setq ed (subst (cons 1 C) (assoc 1 b) b ))
    (entmod ed)
    (setq a(car(entsel "Pick block to change: ")))
    (setq b(entget a))
    (setq ed (subst (cons 2 "32F-DP") (assoc 2 b) b ))
    (entmod ed)
  )
  (WHILE (= A "5")
    (SETQ A(CAR(ENTSEL "Pick TEXT TO CHANGE : ")))
    (SETQ B(ENTGET  A))
    (SETQ C "50")
    (setq ed (subst (cons 1 C) (assoc 1 b) b ))
    (entmod ed)
    (setq a(car(entsel "Pick block to change: ")))
    (setq b(entget a))
    (setq ed (subst (cons 2 "dp5") (assoc 2 b) b ))
    (entmod ed)
  )
  (WHILE (= A "6")
    (SETQ A(CAR(ENTSEL "Pick TEXT TO CHANGE : ")))
    (SETQ B(ENTGET  A))
    (SETQ C "60")
    (setq ed (subst (cons 1 C) (assoc 1 b) b ))
    (entmod ed)
    (setq a(car(entsel "Pick block to change: ")))
    (setq b(entget a))
    (setq ed (subst (cons 2 "dp10") (assoc 2 b) b ))
    (entmod ed)
  )
  (WHILE (= A "7")
    (SETQ A(CAR(ENTSEL "Pick TEXT TO CHANGE : ")))
    (SETQ B(ENTGET  A))
    (SETQ C "70")
    (setq ed (subst (cons 1 C) (assoc 1 b) b ))
    (entmod ed)
    (setq a(car(entsel "Pick block to change: ")))
    (setq b(entget a))
    (setq ed (subst (cons 2 "dp10") (assoc 2 b) b ))
    (entmod ed)
  )
  (WHILE (= A "8")
    (SETQ A(CAR(ENTSEL "Pick TEXT TO CHANGE : ")))
    (SETQ B(ENTGET  A))
    (SETQ C "80")
    (setq ed (subst (cons 1 C) (assoc 1 b) b ))
    (entmod ed)
    (setq a(car(entsel "Pick block to change: ")))
    (setq b(entget a))
    (setq ed (subst (cons 2 "dp10") (assoc 2 b) b ))
    (entmod ed)
  )
  (WHILE (= A "9")
    (SETQ A(CAR(ENTSEL "Pick TEXT TO CHANGE : ")))
    (SETQ B(ENTGET  A))
    (SETQ C "90")
    (setq ed (subst (cons 1 C) (assoc 1 b) b ))
    (entmod ed)
    (setq a(car(entsel "Pick block to change: ")))
    (setq b(entget a))
    (setq ed (subst (cons 2 "dp10") (assoc 2 b) b ))
    (entmod ed)
  )
  (WHILE (= A "10")
    (SETQ A(CAR(ENTSEL "Pick TEXT TO CHANGE : ")))
    (SETQ B(ENTGET  A))
    (SETQ C "100")
    (setq ed (subst (cons 1 C) (assoc 1 b) b ))
    (entmod ed)
    (setq a(car(entsel "Pick block to change: ")))
    (setq b(entget a))
    (setq ed (subst (cons 2 "dp100") (assoc 2 b) b ))
    (entmod ed)
  )
  (WHILE (= A "20")
    (SETQ A(CAR(ENTSEL "Pick TEXT TO CHANGE : ")))
    (SETQ B(ENTGET  A))
    (SETQ C "200")
    (setq ed (subst (cons 1 C) (assoc 1 b) b ))
    (entmod ed)
    (setq a(car(entsel "Pick block to change: ")))
    (setq b(entget a))
    (setq ed (subst (cons 2 "dp20") (assoc 2 b) b ))
    (entmod ed)
  )
  (WHILE (= A "Q1")
    (SETQ A(CAR(ENTSEL "Pick TEXT TO CHANGE : ")))
    (SETQ B(ENTGET  A))
    (SETQ C "10")
    (setq ed (subst (cons 1 C) (assoc 1 b) b ))
    (entmod ed)
    (setq a(car(entsel "Pick block to change: ")))
    (setq b(entget a))
    (setq ed (subst (cons 2 "PDP1") (assoc 2 b) b ))
    (entmod ed)
  )
  (WHILE (= A "Q2")
    (SETQ A(CAR(ENTSEL "Pick TEXT TO CHANGE : ")))
    (SETQ B(ENTGET  A))
    (SETQ C "20")
    (setq ed (subst (cons 1 C) (assoc 1 b) b ))
    (entmod ed)
    (setq a(car(entsel "Pick block to change: ")))
    (setq b(entget a))
    (setq ed (subst (cons 2 "PDP2") (assoc 2 b) b ))
    (entmod ed)
  )
)
;=================================================================
;Following programs are to change text and blocks of "Sub-Pillars"
;=================================================================
(DEFUN C:PiL()
  (SETQ A(GETSTRING "1/2/3/4/5/6/7/8/9/10/20: "))
  (WHILE (= A "1")
    (SETQ A(CAR(ENTSEL "Pick TEXT TO CHANGE : ")))
    (SETQ B(ENTGET  A))
    (SETQ C "10")
    (setq ed (subst (cons 1 C) (assoc 1 b) b ))
    (entmod ed)
    (setq a(car(entsel "Pick block to change: ")))
    (setq b(entget a))
    (setq ed (subst (cons 2 "SP") (assoc 2 b) b ))
    (entmod ed)
  )
  (WHILE (= A "2")
    (SETQ A(CAR(ENTSEL "Pick TEXT TO CHANGE : ")))
    (SETQ B(ENTGET  A))
    (SETQ C "20")
    (setq ed (subst (cons 1 C) (assoc 1 b) b ))
    (entmod ed)
    (setq a(car(entsel "Pick block to change: ")))
    (setq b(entget a))
    (setq ed (subst (cons 2 "SP") (assoc 2 b) b ))
    (entmod ed)
  )
  (WHILE (= A "3")
    (SETQ A(CAR(ENTSEL "Pick TEXT TO CHANGE : ")))
    (SETQ B(ENTGET  A))
    (SETQ C "30")
    (setq ed (subst (cons 1 C) (assoc 1 b) b ))
    (entmod ed)
    (setq a(car(entsel "Pick block to change: ")))
    (setq b(entget a))
    (setq ed (subst (cons 2 "SP") (assoc 2 b) b ))
    (entmod ed)
  )
  (WHILE (= A "4")
    (SETQ A(CAR(ENTSEL "Pick TEXT TO CHANGE : ")))
    (SETQ B(ENTGET  A))
    (SETQ C "40")
    (setq ed (subst (cons 1 C) (assoc 1 b) b ))
    (entmod ed)
    (setq a(car(entsel "Pick block to change: ")))
    (setq b(entget a))
    (setq ed (subst (cons 2 "SP") (assoc 2 b) b ))
    (entmod ed)
  )
  (WHILE (= A "5")
    (SETQ A(CAR(ENTSEL "Pick TEXT TO CHANGE : ")))
    (SETQ B(ENTGET  A))
    (SETQ C "50")
    (setq ed (subst (cons 1 C) (assoc 1 b) b ))
    (entmod ed)
    (setq a(car(entsel "Pick block to change: ")))
    (setq b(entget a))
    (setq ed (subst (cons 2 "SP") (assoc 2 b) b ))
    (entmod ed)
  )
  (WHILE (= A "6")
    (SETQ A(CAR(ENTSEL "Pick TEXT TO CHANGE : ")))
    (SETQ B(ENTGET  A))
    (SETQ C "60")
    (setq ed (subst (cons 1 C) (assoc 1 b) b ))
    (entmod ed)
    (setq a(car(entsel "Pick block to change: ")))
    (setq b(entget a))
    (setq ed (subst (cons 2 "SP") (assoc 2 b) b ))
    (entmod ed)
  )
  (WHILE (= A "7")
    (SETQ A(CAR(ENTSEL "Pick TEXT TO CHANGE : ")))
    (SETQ B(ENTGET  A))
    (SETQ C "70")
    (setq ed (subst (cons 1 C) (assoc 1 b) b ))
    (entmod ed)
    (setq a(car(entsel "Pick block to change: ")))
    (setq b(entget a))
    (setq ed (subst (cons 2 "SP") (assoc 2 b) b ))
    (entmod ed)
  )
  (WHILE (= A "8")
    (SETQ A(CAR(ENTSEL "Pick TEXT TO CHANGE : ")))
    (SETQ B(ENTGET  A))
    (SETQ C "80")
    (setq ed (subst (cons 1 C) (assoc 1 b) b ))
    (entmod ed)
    (setq a(car(entsel "Pick block to change: ")))
    (setq b(entget a))
    (setq ed (subst (cons 2 "SP") (assoc 2 b) b ))
    (entmod ed)
  )
  (WHILE (= A "9")
    (SETQ A(CAR(ENTSEL "Pick TEXT TO CHANGE : ")))
    (SETQ B(ENTGET  A))
    (SETQ C "90")
    (setq ed (subst (cons 1 C) (assoc 1 b) b ))
    (entmod ed)
    (setq a(car(entsel "Pick block to change: ")))
    (setq b(entget a))
    (setq ed (subst (cons 2 "SP") (assoc 2 b) b ))
    (entmod ed)
  )
  (WHILE (= A "10")
    (SETQ A(CAR(ENTSEL "Pick TEXT TO CHANGE : ")))
    (SETQ B(ENTGET  A))
    (SETQ C "100")
    (setq ed (subst (cons 1 C) (assoc 1 b) b ))
    (entmod ed)
    (setq a(car(entsel "Pick block to change: ")))
    (setq b(entget a))
    (setq ed (subst (cons 2 "SP") (assoc 2 b) b ))
    (entmod ed)
  )
)
;==============================================================================
;Following programs are to insert text and respective blocks of "Sub-Pillars"  
;==============================================================================
(DEFUN C:Pi()
  (defun rt()
  (setq os(getvar "osmode"))
  (setvar "osmode" 512)
  (setq a(getpoint "Pick Nearby End point: "))
  (setq b(getpoint a "Pick Nearby End point: "))
  (setq c(angle a b))
  (setq d(entlast))
  (setq e(entget d))
  (setq f(cdr(assoc 50 e)))
  (setq ed(subst (cons 50 c) (assoc 50 e) e))
  (entmod ed)
  (setvar "osmode" os)
)
  (setq os(getvar "osmode"))
  (setvar "osmode" 16385)
  (SETQ A(GETSTRING "1/2/3/4/5/6/7/8/9/10/20: "))
  (WHILE (= A "1")
    (COMMAND "INSERT" "SP" PAUSE "" "" "0")(rt)
    (COMMAND "INSERT" "PILNUM" PAUSE "" "" "0")
    (SETQ A(ENTLAST))
    (COMMAND "EXPLODE" A "")
    (SETQ A1(ENTLAST))
    (SETQ B(ENTGET  A1))
    (SETQ C "10")
    (setq ed (subst (cons 1 C) (assoc 1 b) b ))
    (entmod ed)
    
  )
  (WHILE (= A "2")
    (COMMAND "INSERT" "SP" PAUSE "" "" "0")(rt)
    (COMMAND "INSERT" "PILNUM" PAUSE "" "" "0")
    (SETQ A(ENTLAST))
    (COMMAND "EXPLODE" A "")
    (SETQ A1(ENTLAST))
    (SETQ B(ENTGET  A1))
    (SETQ C "20")
    (setq ed (subst (cons 1 C) (assoc 1 b) b ))
    (entmod ed)
  )
  (WHILE (= A "3")
    (COMMAND "INSERT" "SP" PAUSE "" "" "0")(rt)
    (COMMAND "INSERT" "PILNUM" PAUSE "" "" "0")
    (SETQ A(ENTLAST))
    (COMMAND "EXPLODE" A "")
    (SETQ A1(ENTLAST))
    (SETQ B(ENTGET  A1))
    (SETQ C "30")
    (setq ed (subst (cons 1 C) (assoc 1 b) b ))
    (entmod ed)
  )
  (WHILE (= A "4")
    (COMMAND "INSERT" "SP" PAUSE "" "" "0")(rt)
    (COMMAND "INSERT" "PILNUM" PAUSE "" "" "0")
    (SETQ A(ENTLAST))
    (COMMAND "EXPLODE" A "")
    (SETQ A1(ENTLAST))
    (SETQ B(ENTGET  A1))
    (SETQ C "40")
    (setq ed (subst (cons 1 C) (assoc 1 b) b ))
    (entmod ed)
  )
  (WHILE (= A "5")
    (COMMAND "INSERT" "SP" PAUSE "" "" "0")(rt)
    (COMMAND "INSERT" "PILNUM" PAUSE "" "" "0")
    (SETQ A(ENTLAST))
    (COMMAND "EXPLODE" A "")
    (SETQ A1(ENTLAST))
    (SETQ B(ENTGET  A1))
    (SETQ C "50")
    (setq ed (subst (cons 1 C) (assoc 1 b) b ))
    (entmod ed)
  )
  (WHILE (= A "6")
    (COMMAND "INSERT" "SP" PAUSE "" "" "0")(rt)
    (COMMAND "INSERT" "PILNUM" PAUSE "" "" "0")
    (SETQ A(ENTLAST))
    (COMMAND "EXPLODE" A "")
    (SETQ A1(ENTLAST))
    (SETQ B(ENTGET  A1))
    (SETQ C "60")
    (setq ed (subst (cons 1 C) (assoc 1 b) b ))
    (entmod ed)
  )
  (WHILE (= A "7")
    (COMMAND "INSERT" "SP" PAUSE "" "" "0")(rt)
    (COMMAND "INSERT" "PILNUM" PAUSE "" "" "0")
    (SETQ A(ENTLAST))
    (COMMAND "EXPLODE" A "")
    (SETQ A1(ENTLAST))
    (SETQ B(ENTGET  A1))
    (SETQ C "70")
    (setq ed (subst (cons 1 C) (assoc 1 b) b ))
    (entmod ed)
  )
  (WHILE (= A "8")
    (COMMAND "INSERT" "SP" PAUSE "" "" "0")(rt)
    (COMMAND "INSERT" "PILNUM" PAUSE "" "" "0")
    (SETQ A(ENTLAST))
    (COMMAND "EXPLODE" A "")
    (SETQ A1(ENTLAST))
    (SETQ B(ENTGET  A1))
    (SETQ C "80")
    (setq ed (subst (cons 1 C) (assoc 1 b) b ))
    (entmod ed)
  )
  (WHILE (= A "9")
    (COMMAND "INSERT" "SP" PAUSE "" "" "0")(rt)
    (COMMAND "INSERT" "PILNUM" PAUSE "" "" "0")
    (SETQ A(ENTLAST))
    (COMMAND "EXPLODE" A "")
    (SETQ A1(ENTLAST))
    (SETQ B(ENTGET  A1))
    (SETQ C "90")
    (setq ed (subst (cons 1 C) (assoc 1 b) b ))
    (entmod ed)
  )
  (WHILE (= A "10")
    (COMMAND "INSERT" "SP" PAUSE "" "" "0")(rt)
    (COMMAND "INSERT" "PILNUM" PAUSE "" "" "0")
    (SETQ A(ENTLAST))
    (COMMAND "EXPLODE" A "")
    (SETQ A1(ENTLAST))
    (SETQ B(ENTGET  A1))
    (SETQ C "100")
    (setq ed (subst (cons 1 C) (assoc 1 b) b ))
    (entmod ed)
  )
  (WHILE (= A "20")
    (COMMAND "INSERT" "SP" PAUSE "" "" "0")(rt)
    (COMMAND "INSERT" "PILNUM" PAUSE "" "" "0")
    (SETQ A(ENTLAST))
    (COMMAND "EXPLODE" A "")
    (SETQ A1(ENTLAST))
    (SETQ B(ENTGET  A1))
    (SETQ C(GETSTRING "\nEnter PILLAR CAPACITY: "))
    (setq ed (subst (cons 1 C) (assoc 1 b) b ))
    (entmod ed)
  )
  (setvar "osmode" os)
)
(defun c:ij()
  (setq os(getvar "osmode"))
  (setvar "osmode" 16385)
  (COMMAND "INSERT" "j" PAUSE "" "" "0")
  (setvar "osmode" os)
)
;==============================================================================
;Following programs are to insert text and respective blocks of "DPs"
;==============================================================================
(DEFUN C:DPI()
  (defun rt()
  (setq os(getvar "osmode"))
  (setvar "osmode" 512)
  (setq a(getpoint "Pick Nearby End point: "))
  (setq b(getpoint a "Pick Nearby End point: "))
  (setq c(angle a b))
  (setq d(entlast))
  (setq e(entget d))
  (setq f(cdr(assoc 50 e)))
  (setq ed(subst (cons 50 c) (assoc 50 e) e))
  (entmod ed)
  (setvar "osmode" os)
)
  (setq os(getvar "osmode"))
  (setvar "osmode" 16385)
  (SETQ A(strcase(GETSTRING "1/2/3/4/5/6/7/8/9/10/20/Q1/Q2: ")))
  (WHILE (= A "1")
    (COMMAND "INSERT" "24F-Pole" PAUSE "" "" "0")(rt)
    (COMMAND "INSERT" "PILNUM" PAUSE "" "" "0")
    (SETQ A(ENTLAST))
    (COMMAND "EXPLODE" A "")
    (SETQ A1(ENTLAST))
    (SETQ B(ENTGET  A1))
    (SETQ C "10")
    (setq ed (subst (cons 1 C) (assoc 1 b) b ))
    (entmod ed)
  )
  (WHILE (= A "2")
    (COMMAND "INSERT" "32F-Pole" PAUSE "" "" "0")(rt)
    (COMMAND "INSERT" "PILNUM" PAUSE "" "" "0")
    (SETQ A(ENTLAST))
    (COMMAND "EXPLODE" A "")
    (SETQ A1(ENTLAST))
    (SETQ B(ENTGET  A1))
    (SETQ C "20")
    (setq ed (subst (cons 1 C) (assoc 1 b) b ))
    (entmod ed)
  )
  (WHILE (= A "3")
    (COMMAND "INSERT" "24F-DP" PAUSE "" "" "0")(rt)
    (COMMAND "INSERT" "PILNUM" PAUSE "" "" "0")
    (SETQ A(ENTLAST))
    (COMMAND "EXPLODE" A "")
    (SETQ A1(ENTLAST))
    (SETQ B(ENTGET  A1))
    (SETQ C "30")
    (setq ed (subst (cons 1 C) (assoc 1 b) b ))
    (entmod ed)
  )
  (WHILE (= A "4")
    (COMMAND "INSERT" "32F-DP" PAUSE "" "" "0")(rt)
    (COMMAND "INSERT" "PILNUM" PAUSE "" "" "0")
    (SETQ A(ENTLAST))
    (COMMAND "EXPLODE" A "")
    (SETQ A1(ENTLAST))
    (SETQ B(ENTGET  A1))
    (SETQ C "40")
    (setq ed (subst (cons 1 C) (assoc 1 b) b ))
    (entmod ed)
  )
  (WHILE (= A "5")
    (COMMAND "INSERT" "DP5" PAUSE "" "" "0")(rt)
    (COMMAND "INSERT" "PILNUM" PAUSE "" "" "0")
    (SETQ A(ENTLAST))
    (COMMAND "EXPLODE" A "")
    (SETQ A1(ENTLAST))
    (SETQ B(ENTGET  A1))
    (SETQ C "50")
    (setq ed (subst (cons 1 C) (assoc 1 b) b ))
    (entmod ed)
  )
  (WHILE (= A "6")
    (COMMAND "INSERT" "DP10" PAUSE "" "" "0")(rt)
    (COMMAND "INSERT" "PILNUM" PAUSE "" "" "0")
    (SETQ A(ENTLAST))
    (COMMAND "EXPLODE" A "")
    (SETQ A1(ENTLAST))
    (SETQ B(ENTGET  A1))
    (SETQ C "60")
    (setq ed (subst (cons 1 C) (assoc 1 b) b ))
    (entmod ed)
  )
  (WHILE (= A "7")
    (COMMAND "INSERT" "DP10" PAUSE "" "" "0")(rt)
    (COMMAND "INSERT" "PILNUM" PAUSE "" "" "0")
    (SETQ A(ENTLAST))
    (COMMAND "EXPLODE" A "")
    (SETQ A1(ENTLAST))
    (SETQ B(ENTGET  A1))
    (SETQ C "70")
    (setq ed (subst (cons 1 C) (assoc 1 b) b ))
    (entmod ed)
  )
  (WHILE (= A "8")
    (COMMAND "INSERT" "DP10" PAUSE "" "" "0")(rt)
    (COMMAND "INSERT" "PILNUM" PAUSE "" "" "0")
    (SETQ A(ENTLAST))
    (COMMAND "EXPLODE" A "")
    (SETQ A1(ENTLAST))
    (SETQ B(ENTGET  A1))
    (SETQ C "80")
    (setq ed (subst (cons 1 C) (assoc 1 b) b ))
    (entmod ed)
  )
  (WHILE (= A "9")
    (COMMAND "INSERT" "DP10" PAUSE "" "" "0")(rt)
    (COMMAND "INSERT" "PILNUM" PAUSE "" "" "0")
    (SETQ A(ENTLAST))
    (COMMAND "EXPLODE" A "")
    (SETQ A1(ENTLAST))
    (SETQ B(ENTGET  A1))
    (SETQ C "90")
    (setq ed (subst (cons 1 C) (assoc 1 b) b ))
    (entmod ed)
  )
  (WHILE (= A "10")
    (COMMAND "INSERT" "DP10" PAUSE "" "" "0")(rt)
    (COMMAND "INSERT" "PILNUM" PAUSE "" "" "0")
    (SETQ A(ENTLAST))
    (COMMAND "EXPLODE" A "")
    (SETQ A1(ENTLAST))
    (SETQ B(ENTGET  A1))
    (SETQ C "100")s
    (setq ed (subst (cons 1 C) (assoc 1 b) b ))
    (entmod ed)
  )
  (WHILE (= A "20")
    (COMMAND "INSERT" "DP20" PAUSE "" "" "0")(rt)
    (COMMAND "INSERT" "PILNUM" PAUSE "" "" "0")
    (SETQ A(ENTLAST))
    (COMMAND "EXPLODE" A "")
    (SETQ A1(ENTLAST))
    (SETQ B(ENTGET  A1))
    (SETQ C(GETSTRING "\nEnter PILLAR CAPACITY: "))
    (setq ed (subst (cons 1 C) (assoc 1 b) b ))
    (entmod ed)
  )
  (WHILE (= A "Q1")
    (COMMAND "INSERT" "PDP1" PAUSE "" "" "0")(rt)
    (COMMAND "INSERT" "PILNUM" PAUSE "" "" "0")
    (SETQ A(ENTLAST))
    (COMMAND "EXPLODE" A "")
    (SETQ A1(ENTLAST))
    (SETQ B(ENTGET  A1))
    (SETQ C "10")
    (setq ed (subst (cons 1 C) (assoc 1 b) b ))
    (entmod ed)
  )
  (WHILE (= A "Q2")
    (COMMAND "INSERT" "PDP2" PAUSE "" "" "0")(rt)
    (COMMAND "INSERT" "PILNUM" PAUSE "" "" "0")
    (SETQ A(ENTLAST))
    (COMMAND "EXPLODE" A "")
    (SETQ A1(ENTLAST))
    (SETQ B(ENTGET  A1))
    (SETQ C "20")
    (setq ed (subst (cons 1 C) (assoc 1 b) b ))
    (entmod ed)
  )
  (setvar "osmode" os)
)
;===========================================================================================
;Following programs are to edit Joint and insert joint text and Sub-Pillar and "DP" numbers
;===========================================================================================
(defun c:j()
  (SETQ A(SSGET (LIST (CONS 2 "j"))))
  (SETQ BL(STRCAT "*"(GETSTRING "\nEnter BLOCK NAME: ")))
  (SETQ B(SSLENGTH A))
  (SETQ NUM 0)
  (REPEAT B
    (SETQ ON(SSNAME A NUM))
    (SETQ ON1(ENTGET ON))
    (SETQ ONT(CDR(ASSOC 10 ON1)))
    (COMMAND "INSERT" BL ONT "" "" "0")
    (setq num (+ num 1))
  )
)
(DEFUN C:JN()
  (SETQ ON(CAR(ENTSEL "Pick JOINT TEXT: ")))
  (SETQ A(GETSTRING "\nENTER JOINT NUMBER: "))
  (SETQ ON1(ENTGET ON))
  (SETQ ONT(CDR(ASSOC 1 ON1)))
  (SETQ NU(SUBSTR ONT 1 1))
  (SETQ NN(STRCAT NU  A))
  (setq ed (subst (cons 1 nn) (assoc 1 on1) on1 ))
  (entmod ed)
)
(DEFUN C:DD()
  (SETQ ON(CAR(ENTSEL "Pick DP TEXT: ")))
  (SETQ A(GETSTRING "\nEnter DP NUMBER: "))
  (SETQ ON1(ENTGET ON))
  (SETQ ONT(CDR(ASSOC 1 ON1)))
  (SETQ NU(SUBSTR ONT 1 7))
  (SETQ NN(STRCAT NU  A))
  (setq ed (subst (cons 1 nn) (assoc 1 on1) on1 ))
  (entmod ed)
)
(DEFUN C:QQ()
  (SETQ ON(CAR(ENTSEL "Pick SUB-PILLAR TEXT: ")))
  (SETQ A(GETSTRING "ENTETR SUB-PILLAR NUMBER: "))
  (SETQ ON1(ENTGET ON))
  (SETQ ONT(CDR(ASSOC 1 ON1)))
  (SETQ NU(SUBSTR ONT 1 5))
  (SETQ NN(STRCAT NU  A))
  (setq ed (subst (cons 1 nn) (assoc 1 on1) on1 ))
  (entmod ed)
)
(DEFUN C:DPN()
  (SETQ A(GETSTRING "\nEnter fIRST VALUE: "))
  (SETQ NUM(ATOI A))
  (REPEAT 25
    (SETQ NUM1(RTOS NUM 2 0))
    (SETQ NLEN(STRLEN NUM1))
    (IF (= NLEN 1)
      (SETQ NN(STRCAT "0" NUM1))
      (SETQ NN NUM1)
    )
    (setq b(car(entsel "Pick Dp Numbers: ")))
    (while (= b nil)
      (setq b(car(entsel "Pick Dp Numbers: ")))
    )
    (setq c(entget b))
    (setq d(cdr(assoc 1 c)))
    (setq e(SUBSTR d 1 7))
    (setq f(strcat e NN))
    (setq ed (subst (cons 1 f) (assoc 1 c) c))
    (entmod ed)
    (SETQ NUM(ATOI NN))
    (setq num (+ num 1))
  )
)
(DEFUN C:PLN()
  (initget 1)
  (SETQ A(GETSTRING "\nEnter fIRST VALUE: "))
  (SETQ NUM(ATOI A))
  (REPEAT 25
    (SETQ NUM1(RTOS NUM 2 0))
    (SETQ NLEN(STRLEN NUM1))
    (IF (= NLEN 1)
      (SETQ NN(STRCAT "0" NUM1))
      (SETQ NN NUM1)
    )
    (initget 0)
    (setq b(car(entsel "Pick Sub-pillar Number: ")))
    (while (= b nil)
      (setq b(car(entsel "Pick Sub-pillar Number: ")))
      )
    (setq c(entget b))
    (setq d(cdr(assoc 1 c)))
    (setq e(SUBSTR d 1 5))
    (setq f(strcat e NN))
    (setq ed (subst (cons 1 f) (assoc 1 c) c))
    (entmod ed)
    (SETQ NUM(ATOI NN))
    (setq num (+ num 1))
  )
)
(DEFUN C:MPN()
  (SETQ A(GETSTRING "\nEnter fIRST VALUE: "))
  (SETQ NUM(ATOI A))
  (REPEAT 50
    (SETQ NUM1(RTOS NUM 2 0))
    (SETQ NLEN(STRLEN NUM1))
    (IF (= NLEN 1)
      (SETQ NN(STRCAT "0" NUM1))
      (SETQ NN NUM1)
    )
    (setq b(car(entsel "Pick Pillar Numbers: ")))
    (while (= b nil)
      (setq b(car(entsel "Pick Pillar Numbers: ")))
    )
    (setq c(entget b))
    (setq d(cdr(assoc 1 c)))
    (setq e(SUBSTR d 1 3))
    (setq f(strcat e NN))
    (setq ed (subst (cons 1 f) (assoc 1 c) c))
    (entmod ed)
    (SETQ NUM(ATOI NN))
    (setq num (+ num 1))
  )
)
(DEFUN C:jj()
  (SETQ A(GETSTRING "\nEnter fIRST VALUE: "))
  (SETQ NUM(ATOI A))
  (REPEAT 100
    (SETQ NUM1(RTOS NUM 2 0))
    (SETQ NLEN(STRLEN NUM1))
    (COND ((= NLEN 1)(SETQ NN(STRCAT "00" NUM1)))
          ((= NLEN 2)(SETQ NN(STRCAT "0" NUM1)))
	  ((= NLEN 3)(SETQ NN NUM1))
    )
    (setq b(car(entsel "Pick Joints Numbers: ")))
    (while (= b nil)
      (setq b(car(entsel "Pick Joints Numbers: ")))
    )
    (setq c(entget b))
    (setq d(cdr(assoc 1 c)))
    (setq e(SUBSTR d 1 1))
    (setq f(strcat e NN ))
    (setq ed (subst (cons 1 f) (assoc 1 c) c))
    (entmod ed)
    (SETQ NUM(ATOI Num1))
    (setq num (+ num 1))
  )
)
(DEFUN C:jj1()
  (SETQ A(GETSTRING "\nEnter fIRST VALUE: "))
  (SETQ NUM(ATOI A))
  (REPEAT 100
    (SETQ NUM1(RTOS NUM 2 0))
    (SETQ NN NUM1)
    (setq b(car(entsel "Pick Joints Numbers: ")))
    (while (= b nil)
      (setq b(car(entsel "Pick Joints Numbers: ")))
    )
    (setq c(entget b))
    (setq d(cdr(assoc 1 c)))
    (setq e(SUBSTR d 1 1))
    (setq f(strcat e NN ))
    (setq ed (subst (cons 1 f) (assoc 1 c) c))
    (entmod ed)
    (SETQ NUM(ATOI Num1))
    (setq num (+ num 1))
  )
)
(DEFUN C:cp()
  (SETQ A(GETSTRING "\nEnter fIRST VALUE: "))
  (SETQ NUM(ATOI A))
  (REPEAT 25
    (SETQ NUM1(RTOS NUM 2 0))
    (SETQ NLEN(STRLEN NUM1))
    (IF (= NLEN 1)
      (SETQ NN(STRCAT "0" NUM1))
      (SETQ NN NUM1)
    )
    (SETQ DF(cdr(assoc 1(entget(CAR(ENTSEL "Pick PILLAR CAPACITY: "))))))
    (while (= df nil)
      (SETQ DF(cdr(assoc 1(entget(CAR(ENTSEL "Pick PILLAR CAPACITY: "))))))
    )
    (setq df1(atoi df))
    (setq b(car(entsel "Pick Sub-pillar Pairages: ")))
    (while (= b nil)
      (setq b(car(entsel "Pick Sub-pillar Pairages: ")))
      )
    (setq c(entget b))
    (setq d(cdr(assoc 1 c)))
    (setq nen(-(+ num df1) 1))
    (SETQ raj(RTOS Nen 2 0))
    (SETQ f(STRCAT "(" nn "-" raj ")"))
    (setq ed (subst (cons 1 f) (assoc 1 c) c))
    (entmod ed)
    (SETQ NUM(ATOI NN))
    (setq num (+ nen 1))
  )
)
(DEFUN C:RAM()
  (SETQ OT(GETSTRING "\nEnter OLD TEXT: "))
  (SETQ NT(GETSTRING "\nEnter NEW TEXT: "))
  (setq di(getint "\nEnter digit number: "))
  (SETQ TT1(STRCAT OT "*"))
  (SETQ A(SSGET (LIST (CONS 1 TT1))))
  (SETQ B(SSLENGTH A))
  (SETQ NUM 0)
  (REPEAT B
    (SETQ ON(SSNAME A NUM))
    (SETQ ON1(ENTGET ON))
    (SETQ ONT(CDR(ASSOC 1 ON1)))
    (SETQ NU(SUBSTR ONT di))
    (SETQ NN(STRCAT NT NU))
    (setq ed (subst (cons 1 nn) (assoc 1 on1) on1 ))
    (entmod ed)
    (setq num (+ num 1))
  )
)

(DEFUN C:ADJ()
  (setq ADN(getint "\nEnter ADDING number: "))
  (setq stn(getint "\nEnter Starting Number: "))
  (SETQ A(SSGET (LIST(CONS 1 "J*"))))
  (SETQ B(SSLENGTH A))
  (SETQ NUM 0)
  (REPEAT B
    (SETQ ON(SSNAME A NUM))
    (SETQ ON1(ENTGET ON))
    (SETQ ONT(CDR(ASSOC 1 ON1)))
    (SETQ NT(SUBSTR ONT 1 1))
    (SETQ NU(SUBSTR ONT 2 ))
    (SETQ AN1(ATOI NU))
    (if (>= AN1 stn)
      (SETQ AN(+ ADN AN1))(setq an an1)
    )
    (SETQ AT(RTOS AN 2 0))
    (SETQ NLEN1(STRLEN AT))
    (COND ((= NLEN1 1)(SETQ NN(STRCAT "00" AT)))
          ((= NLEN1 2)(SETQ NN(STRCAT "0" AT)))
	  ((= NLEN1 3)(SETQ NN AT))
    )
    (SETQ NU(STRCAT NT NN))
    (setq ed (subst (cons 1 nU) (assoc 1 on1) on1 ))
    (entmod ed)
    (setq num (+ num 1))
  )
)
(DEFUN C:SBJ()
  (setq ADN(getint "\nEnter SUBSTRACTING number: "))
  (setq stn(getint "\nEnter Starting Number: "))
  (SETQ A(SSGET(list (cons 1 "J*"))))
  (SETQ B(SSLENGTH A))
  (SETQ NUM 0)
  (REPEAT B
    (SETQ ON(SSNAME A NUM))
    (SETQ ON1(ENTGET ON))
    (SETQ ONT(CDR(ASSOC 1 ON1)))
    (SETQ NT(SUBSTR ONT 1 1))
    (SETQ NU(SUBSTR ONT 2 ))
    (SETQ AN1(ATOI NU))
    (if (>= AN1 stn)
      (SETQ AN(- ADN AN1))(setq an an1)
    )
    (SETQ AN2(ABS AN))
    (SETQ AT(RTOS AN2 2 0))
    (SETQ NLEN1(STRLEN AT))
    (COND ((= NLEN1 1)(SETQ NN(STRCAT "00" AT)))
          ((= NLEN1 2)(SETQ NN(STRCAT "0" AT)))
	  ((= NLEN1 3)(SETQ NN AT))
    )
    (SETQ NU(STRCAT NT NN))
    (setq ed (subst (cons 1 nU) (assoc 1 on1) on1 ))
    (entmod ed)
    (setq num (+ num 1))
  )
)
(DEFUN C:ADp()
  (setq ADN(getint "\nEnter ADDING number: "))
  (SETQ A(SSGET (list (cons 1 "JNR*"))))
  (SETQ B(SSLENGTH A))
  (SETQ NUM 0)
  (REPEAT B
    (SETQ ON(SSNAME A NUM))
    (SETQ ON1(ENTGET ON))
    (SETQ ONT(CDR(ASSOC 1 ON1)))
    (SETQ NT(SUBSTR ONT 1 3))
    (SETQ NU(SUBSTR ONT 4 ))
    (SETQ AN1(ATOI NU))
    (SETQ AN(+ ADN AN1))
    (SETQ AT(RTOS AN 2 0))
    (SETQ NLEN1(STRLEN AT))
    (COND ((= NLEN1 1)(SETQ NN(STRCAT "0" AT)))
          ((= NLEN1 2)(SETQ NN AT))
    )
    (SETQ NU(STRCAT NT NN))
    (setq ed (subst (cons 1 nU) (assoc 1 on1) on1 ))
    (entmod ed)
    (setq num (+ num 1))
  )
)
(defun c:ad()
  (setq a(ssget (list (cons 0 "Text"))))
  (setq b(sslength a))
  (setq num 0)
  (setq v 0)
  (repeat b
    (setq c(atoi(cdr(assoc 1(entget(ssname a num))))))
    (setq tv(+ v c))
    (setq v tv)
    (setq num(+ num 1))
    )
  (setq pv(strcase(strcat "Total = " (rtos tv 2 3))))
  (princ pv)(princ)
  )        
;==============================================================================
;Following programs are to control layers                                      
;==============================================================================
(DEFUN C:BB()
  (SSGET "X" (LIST (CONS 2 "*")))
)
(DEFUN C:5()
  (COMMAND "LAYER" "S" "0" "OFF" "*" "" "ON" "AR,RD,TXT,rd_txt,rd-txt" "" "")
)
(DEFUN C:3()
  (command "layer" "S" "0" "off" "Bldg,road-width,bldg-text,rd-text,bldg-no,AR,LEGEND,RD,RD_TXT,TXT" "")
)
(defun c:sm()
  (setq a(getstring "\nEnter Ab: "))
  (setq b(strcat a "*"))
  (setq c(ssget "x"(list (cons 1 b))))
  (command "change" c "" "p" "la" "text" "")
)
(defun c:sm1()
  (setq c(ssget "x"(list (cons 1 "*P"))))
  (command "change" c "" "p" "la" "CABLE_TXT" "")
)
;==============================================================================
;Following programs are to GET DATABASE TAGS                                      
;==============================================================================
(DEFUN C:bad ()
	(setq a (getstring "\nEnter table name:"))
	(setq b (getstring "\nEnter field name:"))
	(Setq cl (getvar "clayer"))
  (setq h (getreal "enter text height: "))
	(SETQ c (SSGET "X" (list (cons 0 "point") (cons 8 cl))))
	(SETQ LEN (SSLENGTH c))
        (SETQ zz 0)
     (REPEAT LEN
        (SETQ d (SSNAME c zz))
       	(setq ins (cdr (assoc 10 (entget d))))
        (setq value (ade_odgetfield d a b 0))
       	(command "text" "j" "m" ins h "" value "")
         (SETQ zz (+ 1 zz))
     )
  	
  )

(DEFUN C:bad1 ()
	(setq a (getstring "\nEnter table name:"))
	(setq b (getstring "\nEnter field name:"))
	(Setq cl (getvar "clayer"))
  (setq h (getreal "enter text height: "))
	(SETQ c (SSGET "X" (list (cons 0 "lwpolyline") (cons 8 cl))))
	(SETQ LEN (SSLENGTH c))
        (SETQ zz 0)
     (REPEAT LEN
        (SETQ d (SSNAME c zz))
       	(setq ins (cdr (assoc 10 (entget d))))
        (setq value (ade_odgetfield d a b 0))
       (command "text" "j" "m" ins h "" value "")
         (SETQ zz (+ 1 zz))
     )
  	
  )

(DEFUN C:bad2 ()
	(setq a "a1")
	(setq b "name")
	(Setq cl (getvar "clayer"))
        (setq h 2.5)
	(SETQ c(car(entsel "Pick Center Line: ")))
        (setq pt(Getpoint "Pick POint: "))
	(setq ins (cdr (assoc 10 (entget c))))
        (setq value (ade_odgetfield c a b 0))
        (command "text" "j" "m" pt h "" value "")
        (command "change" c "" "p" "c" 2 "")
 )
;==============================================================================

(DEFUN C:TER()
  (SETQ obj(CAR(ENTSEL "Pick text to change: ")))
  (setq ent(entget obj))
  (SETQ CID(GETSTRING "\nEnter Cable_ID: "))
  (SETQ Ccp(GETSTRING "\nEnter Cable-capacity: "))
  (SETQ Cld(GETSTRING "\nEnter Cable-load: "))
  (SETQ tp(STRCASE(GETSTRING "\nEnter Type of Element: ")))
  (SETQ ste(GETSTRING "\nEnter Starting Element no: "))
  (SETQ ede(GETSTRING "\nEnter Starting Element no: "))
  (if (= tp "S")
    (setq tpe "sp")
    )
  (if (= tp "P")
    (setq tpe "PILLAR")
    )
  (if (= tp "D")
    (setq tpe "dp")
    )
  (IF (= EDE "")
    (SETQ PN(STRCAT "(" STE ")"))
     (SETQ PN(STRCAT "(" STE "-" EDE ")"))
    )
  (setq ftl
	 (strcat "cable-" cid " " ccp "(" cld ")" " x 0.4" "[" tpe " no." PN "]"))
  (setq ft(strcase ftl))
  (setq ed(subst (cons 1 ft)(assoc 1 ent) ent))
  (entmod ed)
)
(DEFUN C:ter1()
  (princ "To Automatically change ter number of selected text")
  (SETQ A(GETSTRING "ENTER fIRST VALUE: "))
  (SETQ NUM(ATOI A))
  (REPEAT 100
    (SETQ NUM1(RTOS NUM 2 0))
    (SETQ NLEN(STRLEN NUM1))
    (IF (= NLEN 1)
      (SETQ NN(STRCAT "0" NUM1))
      (SETQ NN NUM1)
    )
    (setq b(car(entsel "Pick Numbers: ")))
    (while (= b nil)
      (setq b(car(entsel "Pick Numbers: ")))
    )
    (setq c(entget b))
    (setq ed (subst (cons 1 nn) (assoc 1 c) c))
    (entmod ed)
    (SETQ NUM(ATOI Num1))
    (setq num (+ num 100))
  )
)

(defun c:check()
  (setq an(strcase(getstring "\nEnter Area Name: ")))
  (setq ss(strcat an "*"))
  (SETQ SL(ssget "x"(list (cons 1 ss))))
  (SETQ SLN(SSLENGTH SL))
  (SETQ NUM 0)
  (SETQ NUM1 1)
  (REPEAT SLN
    (SETQ A(SSNAME SL NUM))
    (SETQ B(CDR(ASSOC 1(ENTGET A))))
    (REPEAT SLN
      (SETQ C(SSNAME SL NUM1))
      (SETQ D(CDR(ASSOC 1(ENTGET C))))
      (IF (= B D)
	(SETQ PV(STRCAT B "=" D))
	)
      (SETQ NUM1(+ NUM1 1))
    )
    (SETQ NUM(+ NUM 1))
  )
)
(DEFUN C:TG()
  (SETQ A(SSGET(LIST (CONS 0 "text"))))
  (SETQ B(SSLENGTH A))
  (SETQ NUM 0)
  (SETQ SUM 0)
  (REPEAT B
    (SETQ C(SSNAME A NUM))
    (SETQ D(CDR(ASSOC 1 (ENTGET C))))
    (SETQ E(ATOI D))
    (SETQ NUM (+ NUM 1))
    (SETQ SUM1(+ SUM E))
    (SETQ SUM SUM1)
    )
  (SETQ VAL(RTOS SUM1 2 2))
  (SETQ PV(STRCAT "TOTAL NUMBER OF TAGS IN THIS PILLAR=" VAL ))
  (PRINC PV)(PRINC)
)
(defun c:da()
  (setq a(ssget "x"(list (cons 8 "legend")(cons 1 "DATE :*"))))
  (setq d(ssname a 0))
  (setq e(entget d))
  (setq b(getstring "\nEnter Date: "))
  (setq c(strcat "DATE : " b))
  (setq ed(subst (cons 1 c)(assoc 1 e) e))
  (entmod ed)
)
(DEFUN C:2()
  (SETQ D(CAR(ENTSEL "Pick TEXT TO CHANGE: ")))
  (while (= d nil)
      (SETQ D(CAR(ENTSEL "Pick TEXT TO CHANGE: ")))
  )
  (SETQ A(GETSTRING "Enter FIRST VALUE: "))
  (SETQ B(GETSTRING "Enter SECOND VALUE: "))
  (SETQ C(STRCAT "(" A "-" B ")"))
  (SETQ E(ENTGET D))
  (setq ed (subst (cons 1 C) (assoc 1 E) E ))
    (entmod ed)
)
(defun c:pct()
  (princ "Make Cabtxt block")(princ)
(defun rt()
  (setq os(getvar "osmode"))
  (setvar "osmode" 512)
  (setq a(getpoint "Pick Nearby End point: "))
  (setq b(getpoint a "Pick Nearby End point: "))
  (setq c(angle a b))
  (setq d(car(entsel "Pick Text to Align: ")))
  (while (= d nil)
      (setq d(car(entsel "Pick Text to Align: ")))
  )
  (setq e(entget d))
  (setq f(cdr(assoc 50 e)))
  (setq ed(subst (cons 50 c) (assoc 50 e) e))
  (entmod ed)
  (setvar "osmode" os)
)
  (setq a(cdr(assoc 62(entget(car(entsel "Pick Cable: "))))))
  (SETQ cl "XXX")
  (COND  ((= a 4)(SETQ cl "10"))
	 ((= a 11)(SETQ cl "20"))
	 ((= a 32)(SETQ cl "50"))
	 ((= a 200)(SETQ cl "100"))
	 ((= a 5)(SETQ cl "200"))
	 ((= a 149)(SETQ cl "400"))
 	 ((= a 30)(SETQ cl "800"))
	 ((= a 145)(SETQ cl "1200"))
	 ((= a 224)(SETQ cl "1600"))
  )
  (setq os(getvar "osmode"))
  (setvar "osmode" 16385)
  (COMMAND "INSERT" "cabtxt" PAUSE "" "" "0")
  (SETQ cb(ENTLAST))
  (COMMAND "EXPLODE" cb "")
  (SETQ cb1(ENTLAST))
  (setq os(getvar "osmode"))
  (setvar "osmode" 512)
  (setq art(getpoint "Pick Nearby End point: "))
  (setq brt(getpoint art "Pick Nearby End point: "))
  (setq crt(angle art brt))
  (setq ert(entget cb1))
  (setq frt(cdr(assoc 50 ert)))
  (setq ed2(subst (cons 50 crt) (assoc 50 ert) ert))
  (entmod ed2)
  (setvar "osmode" os)
  (SETQ cb2(ENTGET cb1))
  (setq l "")
  (IF (/= cl "10")
    (IF (/= cl "20")
      (IF (/= cl "XXX")
        (setq l(getstring "\nEnter Load :"))
      )
    )
  )
  (setq l1(getstring "\nEnter Distance :"))
  (SETQ SL1(STRLEN L1))
  (SETQ SL(STRLEN L))
  (IF (= SL 0)
    (setq ft cl)
    (setq ft(strcat cl "(" l ")"))
  )
  (IF (= SL1 0)
    (setq ft FT)
    (setq ft(strcat ft "/" l1))
  )
  (setq ed(subst (cons 1 FT)(assoc 1 cb2) cb2))
  (entmod ed)
)

(defun c:pct1()
  (princ "Make Cabtxt block")(princ)
(defun rt()
  (setq os(getvar "osmode"))
  (setvar "osmode" 512)
  (setq a1(getpoint "Pick Nearby End point: "))
  (setq b(getpoint a1 "Pick Nearby End point: "))
  (setq c(angle a1 b))
  (setq d(car(entsel "Pick Text to Align: ")))
  (while (= d nil)
      (setq d(car(entsel "Pick Text to Align: ")))
  )
  (setq e(entget d))
  (setq f(cdr(assoc 50 e)))
  (setq ed(subst (cons 50 c) (assoc 50 e) e))
  (entmod ed)
  (setvar "osmode" os)
)
  (command "line" "0,0" "0,0" "")
  (setq eta(entlast))
  (command "lengthen" eta "")
  (command "erase" eta "")
  (Setq ent(car(entsel "Pick Cable: ")))
  (setq a(cdr(assoc 62(entget ent))))
  (SETQ cl "XXX")
  (COND  ((= a 4)(SETQ cl "10"))
	 ((= a 11)(SETQ cl "20"))
	 ((= a 32)(SETQ cl "50"))
	 ((= a 200)(SETQ cl "100"))
	 ((= a 5)(SETQ cl "200"))
	 ((= a 149)(SETQ cl "400"))
 	 ((= a 30)(SETQ cl "800"))
	 ((= a 145)(SETQ cl "1200"))
	 ((= a 224)(SETQ cl "1600"))
  )
  (setq os(getvar "osmode"))
  (setvar "osmode" 16385)
  (COMMAND "INSERT" "cabtxt" PAUSE "" "" "0")
  (SETQ cb(ENTLAST))
  (COMMAND "EXPLODE" cb "")
  (SETQ cb1(ENTLAST))
  (setq os(getvar "osmode"))
  (setvar "osmode" 512)
  (setq art(getpoint "Pick Nearby End point: "))
  (setq brt(getpoint art "Pick Nearby End point: "))
  (setq crt(angle art brt))
  (setq ert(entget cb1))
  (setq frt(cdr(assoc 50 ert)))
  (setq ed2(subst (cons 50 crt) (assoc 50 ert) ert))
  (entmod ed2)
  (setvar "osmode" os)
  (SETQ cb2(ENTGET cb1))
  (setq l "")
  (IF (/= cl "10")
    (IF (/= cl "20")
      (IF (/= cl "XXX")
        (setq l(getstring "\nEnter Load :"))
      )
    )
  )
  (COMMAND "LENGTHEN" ent "")
  (SETQ VL(GETVAR "PERIMETER"))
  (setq l1(rtos vl 2 0))
  (SETQ SL1(STRLEN L1))
  (SETQ SL(STRLEN L))
  (IF (= SL 0)
    (setq ft cl)
    (setq ft(strcat cl "(" l ")"))
  )
  (IF (= SL1 0)
    (setq ft FT)
    (setq ft(strcat ft "/" l1))
  )
  (setq ed(subst (cons 1 FT)(assoc 1 cb2) cb2))
  (entmod ed)
  )
(defun c:pctf()
;(princ "Command to insert cable-text with substaction dist")
(defun rt()
  (setq os(getvar "osmode"))
  (setvar "osmode" 512)
  (setq a(getpoint "Pick Nearby End point: "))
  (setq b(getpoint a "Pick Nearby End point: "))
  (setq c(angle a b))
  (setq d(car(entsel "Pick Text to Align: ")))
  (while (= d nil)
      (setq d(car(entsel "Pick Text to Align: ")))
  )
  (setq e(entget d))
  (setq f(cdr(assoc 50 e)))
  (setq ed(subst (cons 50 c) (assoc 50 e) e))
  (entmod ed)
  (setvar "osmode" os)
)
  (setq a(cdr(assoc 62(entget(car(entsel "Pick Cable: "))))))
  (SETQ cl "XXX")
  (COND  ((= a 4)(SETQ cl "10"))
	 ((= a 11)(SETQ cl "20"))
	 ((= a 32)(SETQ cl "50"))
	 ((= a 200)(SETQ cl "100"))
	 ((= a 5)(SETQ cl "200"))
	 ((= a 149)(SETQ cl "400"))
 	 ((= a 30)(SETQ cl "800"))
	 ((= a 145)(SETQ cl "1200"))
	 ((= a 224)(SETQ cl "1600"))
  )
  (setq os(getvar "osmode"))
  (setvar "osmode" 16385)
  (COMMAND "INSERT" "cabtxt" PAUSE "" "" "0")
  (SETQ cb(ENTLAST))
  (COMMAND "EXPLODE" cb "")
  (SETQ cb1(ENTLAST))
  (setq os(getvar "osmode"))
  (setvar "osmode" 512)
  (setq art(getpoint "Pick Nearby End point: "))
  (setq brt(getpoint art "Pick Nearby End point: "))
  (setq crt(angle art brt))
  (setq ert(entget cb1))
  (setq frt(cdr(assoc 50 ert)))
  (setq ed2(subst (cons 50 crt) (assoc 50 ert) ert))
  (entmod ed2)
  (setvar "osmode" os)
  (SETQ cb2(ENTGET cb1))
  (setq l "")
  (IF (/= cl "10")
    (IF (/= cl "20")
      (IF (/= cl "XXX")
        (setq l(getstring "\nEnter Load :"))
      )
    )
  )
  (setq lx(getint "\nEnter value :"))
  (setq ly(getint "\nEnter sub value :"))
  (if (= lx nil)
    (setq lx 0)
    )
  (if (= ly nil)
    (setq ly 0)
    )
  (setq l1(rtos(abs(- lx ly)) 2 0))
  (if (= l1 "0")
    (setq l1 "XXX")
    )
  (SETQ SL1(STRLEN L1))
  (SETQ SL(STRLEN L))
  (IF (= SL 0)
    (setq ft cl)
    (setq ft(strcat cl "(" l ")"))
  )
  (IF (= SL1 0)
    (setq ft FT)
    (setq ft(strcat ft "/" l1))
  )
  (setq ed(subst (cons 1 FT)(assoc 1 cb2) cb2))
  (entmod ed)
  )

(defun c:q1()
  (setq a(car(entsel "Pick Cable Text My Dear Loki: ")))
  (setq b(entget a))
  (setq d(cdr(assoc 1 b)))
  (setq c(getstring "\nEnter Dist Mr Satish: "))
  (setq e(strcat d "/" c))
  (setq ed(subst (cons 1 e)(assoc 1 b) b))
  (entmod ed)
)
(defun c:q()
  (setq a(car(entsel "Pick Cable Text : ")))
  (setq b(entget a))
  (setq c(getstring "Enter uti : "))
  (setq d(getstring "Enter cap : "))
  (setq e(strcat c "/" d))
  (setq ed(subst (cons 1 e)(assoc 1 b) b))
  (entmod ed)
)
(defun c:t()
  (setq a(car(entsel "Pick pairage  ")))
  (setq b(entget a))
  (setq d(cdr(assoc 1 b)))
  (setq e(strcat d "(E)"))
  (setq ed(subst (cons 1 e)(assoc 1 b) b))
  (entmod ed)
)
(defun c:ty()
  (setq a(car(entsel "Pick pairage  ")))
  (setq b(entget a))
  (setq d(cdr(assoc 1 b)))
  (setq e(strcat d "n"))
  (setq ed(subst (cons 1 e)(assoc 1 b) b))
  (entmod ed)
)
;-----------------------------------------------------------------
;plotting                                                         
;-----------------------------------------------------------------
(defun c:plt()
  (initget 1 "A0 A1 A2 A3 A4")
  (setq ps1 (getkword "\nEnter Paper Size <A0/A1/A2/A3/A4>:"))
  (initget 1 "L P")
  (SETQ PP(strcase
	    (Getkword "\nEnter Paper Oreintation <Landscape/Potrait> :")))
  (if (= pp "L")
  (cond ((= ps1 "A0")(setq ps "ISO A0 - 841 x 1189 mm."))
	((= ps1 "A1")(setq ps "ISO A1 - 594 x 841 mm. (landscape)."))
	((= ps1 "A2")(setq ps "ISO A2 - 420 x 594 mm. (landscape)"))
	((= ps1 "A3")(setq ps "ISO A3 - 297 x 420 mm. (landscape)"))
	((= ps1 "A4")(setq ps "ISO A4 - 210 x 297 mm. (portrait)"))
	))
  (if (= pp "P")
  (cond ((= ps1 "A0")(setq ps "ISO A0 - 841 x 1189 mm."))
	((= ps1 "A1")(setq ps "ISO A1 - 594 x 841 mm. (portrait)."))
	((= ps1 "A2")(setq ps "ISO A2 - 420 x 594 mm. (portrait)"))
	((= ps1 "A3")(setq ps "ISO A3 - 297 x 420 mm. (portrait)"))
	((= ps1 "A4")(setq ps "ISO A4 - 210 x 297 mm. (portrait)"))
	))
  (initget 1 "L p")
  (setq pt (getkword "\nEnter  <Landscape/Potrait>:"))
  (command "plot" "y" "model" "hpgis" ps "m"
	   "Landscape" "n" "e" "f" "c" "y"
	   "acad.ctb" "y" "n" "n" "n" "y")
)
(defun c:plt1()
  (initget 1 "A0 A1 A2 A3 A4")
  (setq ps1 (getkword "\nEnter Paper Size <A0/A1/A2/A3/A4>:"))
  (initget 1 "L P")
  (SETQ PP(strcase
	    (Getkword "\nEnter Paper Oreintation <Landscape/Potrait> :")))
  (if (= pp "L")
  (cond ((= ps1 "A0")(setq ps "ISO A0 - 841 x 1189 mm."))
	((= ps1 "A1")(setq ps "ISO A1 - 594 x 841 mm. (landscape)."))
	((= ps1 "A2")(setq ps "ISO A2 - 420 x 594 mm. (landscape)"))
	((= ps1 "A3")(setq ps "ISO A3 - 297 x 420 mm. (landscape)"))
	((= ps1 "A4")(setq ps "ISO A4 - 210 x 297 mm. (portrait)"))
	))
  (if (= pp "P")
  (cond ((= ps1 "A0")(setq ps "ISO A0 - 841 x 1189 mm."))
	((= ps1 "A1")(setq ps "ISO A1 - 594 x 841 mm. (portrait)."))
	((= ps1 "A2")(setq ps "ISO A2 - 420 x 594 mm. (portrait)"))
	((= ps1 "A3")(setq ps "ISO A3 - 297 x 420 mm. (portrait)"))
	((= ps1 "A4")(setq ps "ISO A4 - 210 x 297 mm. (portrait)"))
	))
  (initget 1 "L p")
  (setq pt (getkword "\nEnter Print Orientation<Landscape/Potrait>:"))
  (setq pw(getpoint "Pick Lower left Corner :"))
  (setq pw1(Getcorner pw "Pick Upper Right Corner :"))
  (command "plot" "y" "model" "hpgis" ps "m"
	   pt "n" "w" pw pw1 "f" "c" "y"
	   "acad.ctb" "y" "n" "n" "n" "y")
)
(defun c:a3()
  (initget 1 "L p")
  (setq pt (getkword "\nEnter Print Orientation<Landscape/Potrait>:"))
  (command "plot" "y" "model" "hpgis" "Oversize: ISO A3  (landscape)" "m"
	   pt "n" "e" "f" "c" "y"
	   "acad.ctb" "y" "n" "n" "n" "y")
)
(defun c:a3w()
  (initget 1 "L p")
  (setq pt (getkword "\nEnter Print Orientation<Landscape/Potrait>:"))
  (setq pw(getpoint "Pick Lower left Corner :"))
  (setq pw1(Getcorner pw "Pick Upper Right Corner :"))
  (command "plot" "y" "model" "hpgis" "Oversize: ISO A3  (landscape)" "m"
	   pt "n" "w" pw pw1 "f" "c" "y"
	   "acad.ctb" "y" "n" "n" "n" "y")
)
(defun c:a2w()
  (initget 1 "L p")
  (setq pt (getkword "\nEnter Print Orientation<Landscape/Potrait>:"))
  (setq pw(getpoint "Pick Lower left Corner :"))
  (setq pw1(Getcorner pw "Pick Upper Right Corner :"))
  (command "plot" "y" "model" "hpgis" "Oversize: ISO A2  (landscape)" "m"
	   pt "n" "w" pw pw1 "f" "c" "y"
	   "acad.ctb" "y" "n" "n" "n" "y")
)
(defun c:pp()
  (command "plot" "y" "model" "hpgis"
	   "ISO A2 - 420 x 594 mm. (landscape)" "m"
	   "Landscape" "n" "e" "f" "c" "y"
	   "acad.ctb" "y" "n" "n" "n" "y")
)
(defun c:ps()
  (command "plot" "y" "model" "hpgis"
	   "ISO A0 - 841 x 1189 mm." "m"
	   "Landscape" "n" "e" "f" "c" "y"
	   "acad.ctb" "y" "n" "n" "n" "y")
)
(defun c:row()
  (COMMAND "LAYER" "S" "0" "OFF" "*" "" "ON" "AR,RD,TXT,row" "" "")
)
(defun c:ppa()
  (defun pp()
  (command "plot" "y" "model" "HP DesignJet 800 42 by HP"
	   "ISO A2 - 420 x 594 mm. (landscape)" "m"
	   "Landscape" "n" "e" "f" "c" "y"
	   "acad.ctb" "y" "n" "n" "n" "y"))
  (defun pac()(COMMAND "LAYER" "S" "0" "on" "*" "")
  (command "purge" "a" "*" "n")(command "purge" "a" "*" "n")
  (command "zoom" "e")(command "qsave")(command "close"))
  (setq a(Getint "\nEnter Number of Copies: "))
  (repeat a (pp))
  (pac)
)
  
;------------------------------------------------------------------
;Sp-pairage Details                                                
;------------------------------------------------------------------
(defun c:spd()
  (SETQ AR(GETSTRING "\nEnter Area ABB: "))
  (setq fdt(strcase(strcat ar "*")))
  (SETQ RT(SSGET "X"(list (cons 8 "text")(cons 1 fdt))))
  (setq sl(sslength rt))
  (SETQ L NIL)
  (REPEAT sl
    (setq el(cdr(assoc 1(entget(car(entsel "Pick Source Text: "))))))
    (SETQ LL(APPEND L (LIST el)))
    (SETQ L LL)
  )
  (alert "Now Please Start Picking in the Table")
  (setq num 0)
  (repeat sl
    (setq ct(car(entsel "Pick Editing Text: ")))
    (setq cte(entget ct))
    (setq ft(nth num ll))
    (setq ed(subst (cons 1 ft)(assoc 1 cte) cte))
    (entmod ed)
    (setq num(+ num 1))
  )
)
(DEFUN C:D()
  (SETQ A(CAR(ENTSEL "Pick PLINE: ")))
  (COMMAND "LENGTHEN" A "")
  (SETQ VL(GETVAR "PERIMETER"))
  (setq vl1(rtos vl 2 0))
  (SETQ B(CAR(ENTSEL "Pick Cable Text: ")))
  (setq c(entget b))
  (setq d(cdr(assoc 1 c)))
  (setq ft(strcat d "/" vl1))
  (setq ed(subst (cons 1 ft)(assoc 1 c) c))
  (entmod ed)
)
(DEFUN C:D1()
  (SETQ B(CAR(ENTSEL "Pick Cable Text: ")))
  (setq a(getstring "Enter Dist :"))
  (setq c(entget b))
  (setq d(cdr(assoc 1 c)))
  (setq ft(strcat d "/" a))
  (setq ed(subst (cons 1 ft)(assoc 1 c) c))
  (entmod ed)
)
(DEFUN C:lst()
  (SETQ A(SSGET(LIST (CONS 0 "TEXT"))))
  (SETQ SL(SSLENGTH A))
  (SETQ NUM 0)
  (SETQ LL NIL)
  (REPEAT SL
    (SETQ B(SSNAME A NUM))
    (SETQ C(CDR(ASSOC 1(ENTGET B))))
    (SETQ D(APPEND LL (LIST C)))
    (SETQ LL D)
    (SETQ NUM(+ NUM 1))
  )
  (SETQ FL(ACAD_STRLSORT LL))
  (PRINC FL)(FL)
)


;Insert Wall-etc
(DEFUN C:spdp()
  (defun rt()
  (setq os(getvar "osmode"))
  (setvar "osmode" 512)
  (setq a(getpoint "Pick Nearby End point: "))
  (setq b(getpoint a "Pick Nearby End point: "))
  (setq c(angle a b))
  (setq d(car(entsel "Pick Text to Align: ")))
  (while (= d nil)
      (setq d(car(entsel "Pick Text to Align: ")))
  )
  (setq e(entget d))
  (setq f(cdr(assoc 50 e)))
  (setq ed(subst (cons 50 c) (assoc 50 e) e))
  (entmod ed)
  (setvar "osmode" os)
)
  (setq os(getvar "osmode"))
  (setvar "osmode" 16385)
  (initget 1 "S W P L")
  (SETQ A(GETkword "S(sp)/W(wall)/P(pole)/l(planned): "))
  (WHILE (= A "W")
    (COMMAND "INSERT" "Wall-DP" PAUSE "1" "1" "0")(rt)
  )
  (WHILE (= A "P")
    (COMMAND "INSERT" "Pole-DP" PAUSE "1" "1" "0")(rt)
  )
  (WHILE (= A "l")
    (COMMAND "INSERT" "Pl-Dp" PAUSE "1" "1" "0")(rt)
  )
  (WHILE (= A "S")
    (COMMAND "INSERT" "Sp" PAUSE ".2" ".2" "0")(rt)
  )
  (setvar "osmode" 0)
)
(DEFUN C:BOQ()
  (SETQ A(GETSTRING "\nEnter cable-Capacity: "))
  (setq num 0)
  (COND ((= a "1600")(SETQ CC 224))
	((= a "1200")(SETQ CC 145))
	((= a "800")(SETQ CC 30))
	((= a "400")(SETQ CC 149))
	((= a "200")(SETQ CC 5))
	((= a "100")(SETQ CC 200))
	((= a "50")(SETQ CC 32))
	((= a "20")(SETQ CC 11))
	((= a "10")(SETQ CC 4))
  )
  (SETQ SS(SSGET (LIST (CONS 0 "LWPOLYLINE")(CONS 62 CC))))
  (SETQ SL(SSLENGTH SS))
  (setq l 0)
  (REPEAT SL
    (SETQ B(SSNAME SS NUM))
    (COMMAND "LENGTHEN" b "")
    (SETQ VL(GETVAR "PERIMETER"))
    (setq l1(+ l vl))
    (setq num(+ num 1))
    (setq l l1)
  )
  (setq fl(strcat "Total Length of" a "Pair Cable =" " " (rtos l1 2 2)))
  (princ fl)(princ)
)
(DEFUN C:lgt()
  (setq num 0)
  (SETQ SS(SSGET (LIST (CONS 0 "LWPOLYLINE"))))
  (SETQ SL(SSLENGTH SS))
  (setq l 0)
  (REPEAT SL
    (SETQ B(SSNAME SS NUM))
    (COMMAND "LENGTHEN" b "")
    (SETQ VL(GETVAR "PERIMETER"))
    (setq l1(+ l vl))
    (setq num(+ num 1))
    (setq l l1)
  )
  (setq fl(strcat "Total Length of Pair Cable =" " " (rtos l1 2 2)))
  (princ fl)(princ)
)
(DEFUN C:BOQ1()
  (command "line" "0,0" "0,0" "")
  (setq sri(entlast))
  (command "lengthen" sri "")
  (command "erase" sri "")
  (setq a(ssget (list (cons 0 "lwpolyline"))))
  (setq sl(sslength a))
  (setq num 0)
  (setq la 0)
  (setq lb 0)
  (setq lc 0)
  (setq ld 0)
  (setq le 0)
  (setq lf 0)
  (setq lg 0)
  (setq lh 0)
  (setq li 0)
  (setq la1 0)
  (setq lb1 0)
  (setq lc1 0)
  (setq ld1 0)
  (setq le1 0)
  (setq lf1 0)
  (setq lg1 0)
  (setq lh1 0)
  (setq li1 0)
  (repeat sl
    (setq an(ssname a num))
    (COMMAND "LENGTHEN" an "")
    (SETQ len(GETVAR "PERIMETER"))
    (setq b(cdr(assoc 62 (entget an))))
    (if(= b 224)(setq la1(+ la len)))
    (if(= b 146)(setq lb1(+ lb len)))
    (if(= b 30)(setq lc1(+ lc len)))
    (if(= b 149)(setq ld1(+ ld len)))
    (if(= b 5)(setq le1(+ le len)))
    (if(= b 200)(setq lf1(+ lf len)))
    (if(= b 32)(setq lg1(+ lg len)))
    (if(= b 11)(setq lh1(+ lh len)))
    (if(= b 4)(setq li1(+ li len)))
    (setq la la1)
    (setq lb lb1)
    (setq lc lc1)
    (setq ld ld1)
    (setq le le1)
    (setq lf lf1)
    (setq lg lg1)
    (setq lh lh1)
    (setq li li1)
    (setq num(+ num 1))
    )
  (setq fla(strcat "\nTotal Length of 1600 Pair Cable =" " "
		   (rtos la1 2 2)))
  (setq flb(strcat "\nTotal Length of 1200 Pair Cable =" " "
		   (rtos lb1 2 2)))
  (setq flc(strcat "\nTotal Length of 800 Pair Cable =" " "
		   (rtos lc1 2 2)))
  (setq fld(strcat "\nTotal Length of 400 Pair Cable =" " "
		   (rtos ld1 2 2)))
  (setq fle(strcat "\nTotal Length of 200 Pair Cable =" " "
		   (rtos le1 2 2)))
  (setq flf(strcat "\nTotal Length of 100 Pair Cable =" " "
		   (rtos lf1 2 2)))
  (setq flg(strcat "\nTotal Length of 50 Pair Cable =" " "
		   (rtos lg1 2 2)))
  (setq flh(strcat "\nTotal Length of 20 Pair Cable =" " "
		   (rtos lh1 2 2)))
  (setq fli(strcat "\nTotal Length of 10 Pair Cable =" " "
		   (rtos li1 2 2)))
  (princ fla)(princ)
  (princ flb)(princ)
  (princ flc)(princ)
  (princ fld)(princ)
  (princ fle)(princ)
  (princ flf)(princ)
  (princ flg)(princ)
  (princ flh)(princ)
  (princ fli)(princ)
  )
(defun c:sps()
  (setq a(ssget (list (cons 2 "p*"))))
  (setq b(sslength a))
  (setq c(strcat "\nTotal Number of Sub-Pillars are = " (rtos b 2 0) ))
  )
(DEFUN C:BOQ2()
  (command "line" "0,0" "0,0" "")
  (setq sri(entlast))
  (command "lengthen" sri "")
  (command "erase" sri "")
  (setq a(ssget (list (cons 0 "lwpolyline"))))
  (setq dp(ssget(list (cons 2 "*"))))
  (setq sl(sslength a))
  (setq sldp(sslength dp))
  (setq num 0)
  (setq num1 0)
  (setq la 0)
  (setq lb 0)
  (setq lc 0)
  (setq ld 0)
  (setq le 0)
  (setq lf 0)
  (setq lg 0)
  (setq lh 0)
  (setq li 0)
  (setq la1 0)
  (setq lb1 0)
  (setq lc1 0)
  (setq ld1 0)
  (setq le1 0)
  (setq lf1 0)
  (setq lg1 0)
  (setq lh1 0)
  (setq li1 0)
  (setq DP1 0
	Dp2 0
	DP5 0
	DP10 0
	DP20 0
	PDP1 0
	PDP2 0
	SP 0)  
  (repeat sl
    (setq an(ssname a num))
    (COMMAND "LENGTHEN" an "")
    (SETQ len(GETVAR "PERIMETER"))
    (setq b(cdr(assoc 62 (entget an))))
    (if(= b 224)(setq la1(+ la len)))
    (if(= b 146)(setq lb1(+ lb len)))
    (if(= b 30)(setq lc1(+ lc len)))
    (if(= b 149)(setq ld1(+ ld len)))
    (if(= b 5)(setq le1(+ le len)))
    (if(= b 200)(setq lf1(+ lf len)))
    (if(= b 32)(setq lg1(+ lg len)))
    (if(= b 11)(setq lh1(+ lh len)))
    (if(= b 4)(setq li1(+ li len)))
    (setq la la1)
    (setq lb lb1)
    (setq lc lc1)
    (setq ld ld1)
    (setq le le1)
    (setq lf lf1)
    (setq lg lg1)
    (setq lh lh1)
    (setq li li1)
    (setq num(+ num 1))
  )
  (Repeat sldp
    (setq DPa(ssname dp num1))
    (setq Dpc(entget DPA))
    (setq DPd(cdr(assoc 2 DPc)))
    (if(= DPD "DP1")(setq DP1a(+ DP1 1)))
    (if(= DPD "DP2")(setq DP2a(+ DP2 1)))
    (if(= DPD "DP5")(setq DP5a(+ DP5 1)))
    (if(= DPD "DP10")(setq DP10a(+ DP10 1)))
    (if(= DPD "DP20")(setq DP20a(+ DP20 1)))
    (if(= DPD "PDP1")(setq PDP1a(+ PDP1 1)))
    (if(= DPD "PDP2")(setq PDP2a(+ PDP2 1)))
    (if(= DPD "SP")(setq SP1(+ SP 1)))
    (setq DP1 DP1a
	  DP2 DP2a
	  DP5 DP5a
	  DP10 DP10a
	  DP20 DP20a
	  PDP1 PDP1a
	  PDP2 PDP2a
	  SP SP1)
    (setq Num1(+ num1 1))
  )
  (setq fla(strcat "\nTotal Length of 1600 Pair Cable =" " "
		   (rtos la1 2 2)))
  (setq flb(strcat "\nTotal Length of 1200 Pair Cable =" " "
		   (rtos lb1 2 2)))
  (setq flc(strcat "\nTotal Length of 800 Pair Cable =" " "
		   (rtos lc1 2 2)))
  (setq fld(strcat "\nTotal Length of 400 Pair Cable =" " "
		   (rtos ld1 2 2)))
  (setq fle(strcat "\nTotal Length of 200 Pair Cable =" " "
		   (rtos le1 2 2)))
  (setq flf(strcat "\nTotal Length of 100 Pair Cable =" " "
		   (rtos lf1 2 2)))
  (setq flg(strcat "\nTotal Length of 50 Pair Cable =" " "
		   (rtos lg1 2 2)))
  (setq flh(strcat "\nTotal Length of 20 Pair Cable =" " "
		   (rtos lh1 2 2)))
  (setq fli(strcat "\nTotal Length of 10 Pair Cable =" " "
		   (rtos li1 2 2)))
  (setq flj(strcat "\nTotal Number of 10 Pair DP =" " "
		   (rtos DP1 2 2)))
  (setq flk(strcat "\nTotal Number of 10 Pair DP =" " "
		   (rtos DP2 2 2)))
  (setq fll(strcat "\nTotal Number of 10 Pair DP =" " "
		   (rtos DP5 2 2)))
  (setq flm(strcat "\nTotal Number of 10 Pair DP =" " "
		   (rtos DP10 2 2)))
  (setq fln(strcat "\nTotal Number of 10 Pair DP =" " "
		   (rtos DP20 2 2)))
  (setq flo(strcat "\nTotal Number of 10 Pair DP =" " "
		   (rtos PDP1 2 2)))
  (setq flp(strcat "\nTotal Number of 10 Pair DP =" " "
		   (rtos PDP2 2 2)))
  (setq flq(strcat "\nTotal Number of 10 Pair DP =" " "
		   (rtos SP 2 2)))
  (princ fla)(princ)
  (princ flb)(princ)
  (princ flc)(princ)
  (princ fld)(princ)
  (princ fle)(princ)
  (princ flf)(princ)
  (princ flg)(princ)
  (princ flh)(princ)
  (princ fli)(princ)
  (princ flj)(princ)
  (princ flk)(princ)
  (princ fll)(princ)
  (princ flm)(princ)
  (princ fln)(princ)
  (princ flo)(princ)
  (princ flp)(princ)
  (princ flq)(princ)
  )
(Defun c:boq5()
  (setq dp(ssget(list (cons 2 "*"))))
  (setq sldp(sslength dp))
  (setq num1 0)
  (setq DP1 0
	Dp2 0
	DP5 0
	DP10 0
	DP20 0
	PDP1 0
	PDP2 0
	SP 0)
  (Repeat sldp
    (setq DPa(ssname dp num1))
    (setq Dpc(entget DPA))
    (setq DPd(cdr(assoc 2 DPc)))
    (if(= DPD "DP1")(setq DP1a(+ DP1 1)))
    (if(= DPD "DP2")(setq DP2a(+ DP2 1)))
    (if(= DPD "DP5")(setq DP5a(+ DP5 1)))
    (if(= DPD "DP10")(setq DP10a(+ DP10 1)))
    (if(= DPD "DP20")(setq DP20a(+ DP20 1)))
    (if(= DPD "PDP1")(setq PDP1a(+ PDP1 1)))
    (if(= DPD "PDP2")(setq PDP2a(+ PDP2 1)))
    (if(= DPD "SP")(setq SP1(+ SP 1)))
    (setq DP1 DP1a
	  DP2 DP2a
	  DP5 DP5a
	  DP10 DP10a
	  DP20 DP20a
	  PDP1 PDP1a
	  PDP2 PDP2a
	  SP SP1)
    (setq num1(+ num1 1))
  )
  (setq flj(strcat "\nTotal Number of 10 Pair DP =" " "
		   (rtos DP1 2 2)))
  (setq flk(strcat "\nTotal Number of 10 Pair DP =" " "
		   (rtos DP2 2 2)))
  (setq fll(strcat "\nTotal Number of 10 Pair DP =" " "
		   (rtos DP5 2 2)))
  (setq flm(strcat "\nTotal Number of 10 Pair DP =" " "
		   (rtos DP10 2 2)))
  (setq fln(strcat "\nTotal Number of 10 Pair DP =" " "
		   (rtos DP20 2 2)))
  (setq flo(strcat "\nTotal Number of 10 Pair DP =" " "
		   (rtos PDP1 2 2)))
  (setq flp(strcat "\nTotal Number of 10 Pair DP =" " "
		   (rtos PDP2 2 2)))
  (setq flq(strcat "\nTotal Number of 10 Pair DP =" " "
		   (rtos SP 2 2)))
   (princ flj)(princ)
  (princ flk)(princ)
  (princ fll)(princ)
  (princ flm)(princ)
  (princ fln)(princ)
  (princ flo)(princ)
  (princ flp)(princ)
  (princ flq)(princ)
  )
(defun c:boq3()
  (setq sp1 0)
  (setq sp2 0)
  (setq sp5 0)
  (setq sp10 0)
  (setq sp(ssget "x"(list (cons 2 "p*"))))
  (setq spa(sslength sp))
  (setq num2 0)
  (repeat spa
    (setq spb(ssname sp num2))
    (setq spc(entget spb))
    (setq spd(cdr(assoc 2 spc)))
    (if(= spd "P1")(setq sp1n(+ sp1 1)))
    (if(= spd "P2")(setq sp2n(+ sp2 1)))
    (if(= spd "P5")(setq sp5n(+ sp5 1)))
    (if(= spd "P10")(setq sp10n(+ sp10 1)))
    (setq num2(+ num2 1))
    (setq sp1 sp1n)
    (setq sp2 sp2n)
    (setq sp5 sp5n)
    (setq sp10 sp10n)
    )
  (setq spta(strcat "Total Number of 10 Pair SPs =" " "
		   (rtos sp1n 2 0)))
  (setq sptb(strcat "Total Number of 20 Pair SPs =" " "
		   (rtos sp2n 2 0)))
  (setq sptc(strcat "Total Number of 50 Pair SPs =" " "
		   (rtos sp5n 2 0)))
  (setq sptd(strcat "Total Number of 100 Pair SPs =" " "
		   (rtos sp10n 2 0)))
  (setq spte(strcat "Total Number of SPs =" " "
		   (rtos total_sp 2 0)))
  (princ spta)(princ)
  (princ sptb)(princ)
  (princ sptc)(princ)
  (princ sptd)(princ)
  (princ spte)(princ)
  )
(defun c:w()
  (setq a(car(entsel "Pick Dim Text: ")))
  (setq b(entget a))
  (setq c(getstring "\nEnter Dist: "))
  (setq e(strcat c "m"))
  (setq ed(subst (cons 1 e)(assoc 1 b) b))
  (entmod ed)
)
(defun c:ms()
  (setq a(ssget))
  (setq b(getint "\nEnter Scale: "))
  (setq num 0)
  (setq le(sslength a))
  (repeat le
  (setq aa(ssname a num))
  (setq a1(entget aa))
  (setq ed (subst (cons 40 b) (assoc 40 a1) a1 ))
  (entmod ed)
  (entupd aa)
  (setq num (+ num 1))
  )
)
(DEFUN C:LM()
  (COMMAND "SCRIPT" "C:/akn/LISP/LAYER.SCR")
  (setq sp(ssget "x" (list (cons 2 "SP"))))
  (command "change" sp "" "p" "la" "sp" "")
  (setq dp(ssget "x" (list (cons 2 "dp*"))))
  (command "change" dp "" "p" "la" "dp" "")
  (setq dp(ssget "x" (list (cons 2 "PDP*"))))
  (command "change" dp "" "p" "la" "dp" "")
  (setq mp(ssget "x" (list (cons 2 "mp"))))
  (command "change" mp "" "p" "la" "mp" "")
  (setq j(ssget "x" (list (cons 2 "j"))))
  (command "change" j "" "p" "la" "JOINTS" "")
  (setq jn(ssget "x" (list (cons 2 "jn"))))
  (command "change" jn "" "p" "la" "Joint_txt" "")
  (setq jn1(ssget "x" (list (cons 8 "0" )(cons 1 "j*"))))
  (command "change" jn1 "" "p" "la" "Joint_txt" "")
  (SETQ DIM(SSGET "X"(LIST (CONS 0 "DIMENSION"))))
  (command "change" DIM "" "p" "la" "DIM" "")
  (SETQ RCC(SSGET "X"(LIST (CONS 0 "MLINE")(CONS 2 "RCC"))))
  (command "change" RCC "" "p" "la" "RCC" "")
  (SETQ GI(SSGET "X"(LIST (CONS 0 "MLINE")(CONS 2 "GI"))))
  (command "change" GI "" "p" "la" "GI" "")
  (SETQ HDD(SSGET "X"(LIST (CONS 0 "MLINE")(CONS 2 "HDD"))))
  (command "change" HDD "" "p" "la" "HDD" "")
  (SETQ PVC(SSGET "X"(LIST (CONS 0 "MLINE")(CONS 2 "PVC"))))
  (command "change" PVC "" "p" "la" "PVC" "")
  (SETQ AS(SSGET "X"(LIST (CONS 0 "MLINE")(CONS 2 "AS"))))
  (command "change" AS "" "p" "la" "ASPHALT" "")
  (SETQ DM(SSGET "X"(LIST (CONS 0 "DIMENSION"))))
  (command "change" DM "" "p" "la" "DIM" "")
)
(defun c:R()
  (initget 1 "R G P H A")
  (setq a(getkword "R(rcc)/G(gi)/P(pvc)/H(hdd)/A(asphalt) :"))
  (COND ((= a "R")(SETQ ms "rcc"))
	((= a "G")(SETQ ms "gi"))
	((= a "P")(SETQ ms "pvc"))
	((= a "H")(SETQ ms "hdd"))
	((= a "A")(SETQ ms "as"))
  )
  (command "mline" "j" "Z" "st" ms)
)
(defun c:RS()
  (SETQ A1(STRCASE(GETSTRING  "\nEnter RSU NAME :")))
  (setq a(car(entsel "Pick SP/DP NUMBER  ")))
  (setq b(entget a))
  (setq d(SUBSTR(cdr(assoc 1 b)) 4))
  (setq e(STRCASE(strcat A1 D)))S
  (setq ed(subst (cons 1 e)(assoc 1 b) b))
  (entmod ed)
)
(defun c:RS1()
  (SETQ A1(STRCASE(GETSTRING  "\nEnter RSU NAME :")))
  (setq a(SSGET(LIST (CONS 8 "TEXT")(CONS 1 "XXX*"))))
  (SETQ SL(SSLENGTH A))
  (SETQ NUM 0)
  (REPEAT SL
    (SETQ B(SSNAME A NUM))
    (SETQ C(ENTGET B))
    (setq d(SUBSTR(cdr(assoc 1 C)) 4))
    (setq e(STRCASE(strcat A1 D)))
    (setq ed(subst (cons 1 e)(assoc 1 C) C))
    (entmod ed)
    (SETQ NUM(+ NUM 1))
  )
)

(defun c:cll()
  (princ "To Change Load")(princ)
  (setq a(car(entsel "Pick Cable-Text to Change: ")))
  (setq vl(Getstring "\nEnter Load :"))
  (setq r(entget a))
  (setq s(cdr(assoc 1 r)))
  (setq b(strlen s))
  (setq f 1)
  (repeat b
    (setq c(substr s f 1))
    (if (= c "(")
      (setq st f)
      )
    (if (= c ")")
      (setq st1 f)
      )
    (setq f(+ f 1))
  )
  (setq fv(substr s 1 st))
  (setq fv1(substr s st1 ))
  (setq ft(strcat fv vl fv1))
  (setq ed (subst (cons 1 ft) (assoc 1 r) r))
  (entmod ed)
)
(DEFUN C:cll1()
  (SETQ D(CAR(ENTSEL "Pick TEXT TO CHANGE: ")))
  (SETQ A(GETSTRING "\nEnter Cable Capacity: "))
  (SETQ B(GETSTRING "\nEnter Cable Load: "))
  (SETQ C(STRCAT A "(" B ")"))
  (SETQ E(ENTGET D))
  (setq ed (subst (cons 1 C) (assoc 1 E) E ))
    (entmod ed)
)
(defun c:cle()
  (princ "To Change length")(princ)
  (setq a(car(entsel "Pick Cable-Text to Change: ")))
  (setq vl(Getstring "\nEnter Length :"))
  (setq r(entget a))
  (setq s(cdr(assoc 1 r)))
  (setq b(strlen s))
  (setq f 1)
  (repeat b
    (setq c(substr s f 1))
    (if (= c "/")
      (setq st f)
      )
    (setq f(+ f 1))
  )
  (setq fv(substr s 1 st))
  (setq ft(strcat fv vl))
  (setq ed (subst (cons 1 ft) (assoc 1 r) r))
  (entmod ed)
)
(defun c:dt1()
  (setq a(strcat (rtos(getreal "\nEnter Dist : ") 2 1) "m"))
  (command "DIMALIGNED" pause pause "t" a pause)
)
(DEFUN C:unkown()
  (SETQ ent(SSGET (LIST (CONS 0 "TEXT"))))
  (SETQ SL(SSLENGTH ENT))
  (setq m 0
        n 0
   	o 0
   	p 0
   	q 0
   	r 0
   	s 0
   	u 0
   	v 0
   	w 0
   	x 0)
  (SETQ NUM 0)
  (REPEAT SL
    (SETQ ent1(SSNAME ent NUM))
    (SETQ ent2(CDR(ASSOC 1(ENTGET ent1))))
      (IF (= ENT2 "10")(SETQ A2(+ 1 m)))
      (IF (= ENT2 "20")(SETQ B2(+ 1 n)))
      (IF (= ENT2 "30")(SETQ C2(+ 1 o)))
      (IF (= ENT2 "40")(SETQ D2(+ 1 p)))
      (IF (= ENT2 "50")(SETQ E2(+ 1 q)))
      (IF (= ENT2 "60")(SETQ F2(+ 1 r)))
      (IF (= ENT2 "70")(SETQ G2(+ 1 s)))
      (IF (= ENT2 "80")(SETQ H2(+ 1 u)))
      (IF (= ENT2 "90")(SETQ I2(+ 1 v)))
      (IF (= ENT2 "100")(SETQ J2(+ 1 w)))
      (IF (= ENT2 "200")(SETQ K2(+ 1 x)))
      (SETQ A A2)
      (SETQ B B2)
      (SETQ C C2)
      (SETQ D D2)
      (SETQ E E2)
      (SETQ F F2)
      (SETQ G G2)
      (SETQ H H2)
      (SETQ I I2)
      (SETQ J J2)
      (SETQ K K2)
      (SETQ NUM(+ NUM 1))
    )
	(setq a1(strcat "total num of 10=" (rtos a2 2 0)))
	(setq b1(strcat "total num of 10=" (rtos b2 2 0)))
	(setq c1(strcat "total num of 10=" (rtos c2 2 0)))
	(setq d1(strcat "total num of 10=" (rtos d2 2 0)))
	(setq e1(strcat "total num of 10=" (rtos e2 2 0)))
	(setq f1(strcat "total num of 10=" (rtos f2 2 0)))
	(setq g1(strcat "total num of 10=" (rtos g2 2 0)))
	(setq h1(strcat "total num of 10=" (rtos h2 2 0)))
	(setq i1(strcat "total num of 10=" (rtos i2 2 0)))
	(setq j1(strcat "total num of 10=" (rtos j2 2 0)))
	(setq k1(strcat "total num of 10=" (rtos k2 2 0)))
 	
)
(defun c:ccp()
  (princ "To Change Cable capacity")(princ)
  (setq a(car(entsel "Pick Cable-Text to Change: ")))
  (setq vl(Getstring "\nEnter Cable-Capacity :"))
  (setq r(entget a))
  (setq s(cdr(assoc 1 r)))
  (setq b(strlen s))
  (setq f 1)
  (repeat b
    (setq c(substr s f 1))
    (if (= c "(")
      (setq st f)
      )
    (setq f(+ f 1))
  )
  (setq fv(substr s st))
  (setq ft(strcat vl fv))
  (setq ed (subst (cons 1 ft) (assoc 1 r) r))
  (entmod ed)
)
(defun c:ccp1()
  (princ "To Change Cable capacity IF NOT THERE")(princ)
  (setq a(car(entsel "Pick Cable-Text to Change: ")))
  (setq vl(Getstring "\nEnter Cable-Capacity :"))
  (setq r(entget a))
  (setq s(cdr(assoc 1 r)))
  (setq b(strlen s))
  (setq f 1)
  (repeat b
    (setq c(substr s f 1))
    (if (= c "/")
      (setq st  f)
      )
    (setq f(+ f 1))
  )
  (setq fv(substr s st))
  (setq ft(strcat vl fv))
  (setq ed (subst (cons 1 ft) (assoc 1 r) r))
  (entmod ed)
)
(defun c:cle1()
  (princ "To \nEnter length if it is not there")(princ)
  (setq a(car(entsel "Pick Cable-Text to Change: ")))
  (setq vl(Getstring "\nEnter Length :"))
  (setq r(entget a))
  (setq s(cdr(assoc 1 r)))
  (setq b(strlen s))
  (setq f 1)
  (repeat b
    (setq c(substr s f 1))
    (if (= c "/")
      (setq st f)
      )
    (setq f(+ f 1))
  )
  (setq st2(abs(- 1 st)))
  (setq fv(substr s 1 st2))
  (setq fv1(substr s st ))
  (setq ft(strcat fv "(" vl ")" fv1))
  (setq ed (subst (cons 1 ft)(assoc 1 r) r))
  (entmod ed)
)
(defun c:4()
  (setq a(ssget (list (cons 0 "text"))))
  (command "change" a "" "p" "c" "bylayer" "")
  )
(defun c:6()
  (command "layer" "off" "PRIMARY_CABLE,sec_cable,joints,JOINTS_TXT,joint_txt,enhacement,spare,joint-txt,cable,sec-cable,sec_cable.dim,hdd,gi,rcc,pvc,cable-txt,cable_txt,DIM,DIMENSION" "")
  )
(defun c:per()
  (setq x(ssget))
  (setq y(sslength x))
  (setq num 0)
  (repeat y
    (setq z(ssname x num))
    (setq z1(entget z))
    (setq z2(cdr(assoc 1 z1)))
    (setq b(strlen z2))
    (setq f 1)
    (repeat b
    (setq c(substr z2 f 1))
    (if (= c "/")
      (setq st f)
      )
    (setq f(+ f 1))
  )
    (setq st2(abs(- 1 st)))
    (setq st3(abs(+ 1 st)))
    (setq fv(substr z2 1 st2))
    (setq fv1(substr z2 st3 ))
    (setq div1(atof fv))
    (setq div2(atof fv1))
    (if (/= div1 0)
      (if (/= div2 0)
    (setq fr(*(/ div1 div2) 100))
	(setq fr 0)
	)
      (setq fr 0)
      )
  (setq ft(strcat z2 "-" (rtos fr 2 0) "%"))
  (setq ed (subst (cons 1 ft)(assoc 1 z1) z1))
  (entmod ed)
    (setq ip(cdr(assoc 10 z1)))
    (if (>= fr 60)
      (command "circle" ip "20")
      )
    (setq num(+ num 1))
    )
)
(defun c:uti()
  (setq a(getstring  "Enter RSU Name with pillar no :"))
  (setq b(strcase(strcat a "*")))
  (setq c(ssget "x"(list (cons 8 "util")(cons 1 b))))
  (setq d(sslength c))
  (repeat d
    (setq x(getstring "Enter Element No :"))
    (setq en(strcase(strcat a x)))
    (setq y(ssget "x"(list (cons 8 "util")(cons 1 en))))
    (while (= y nil)
      (princ (strcat en " " "does not exits"))(princ)
      (setq x(getstring "\nEnter Element No :"))
      (setq en(strcase(strcat a x)))
      (setq y(ssget "x"(list (cons 8 "util")(cons 1 en))))
      )
    (setq ye(ssname y 0))
    (setq y1(entget ye))
    (setq xx1(getstring "Enter Utilisation :"))
    (setq xx2(getstring "Enter Capacity: "))
    (setq x1(strcat xx1 "/" xx2))
    (setq ed(subst (cons 1 x1)(assoc 1 y1)y1))
    (entmod ed)
    )
  )
(defun c:bc()
  (setq a(getstring "Enter Existing BLock Name :"))
  (setq b(getstring "Enter Block to Replace :"))
  (setq c(ssget "x"(list (cons 2 a))))
  (setq sl(sslength c))
  (setq num 0)
  (repeat sl
    (setq d(ssname c num))
    (setq e(entget d))
    (setq ed(subst (cons 2 b)(assoc 2 e)e))
    (entmod ed)
    (setq num(+ num 1))
    )
  (setq pv(strcat (rtos sl 2 0) "no of blocks changed" ))
  (princ pv)(princ)
  )
(DEFUN C:Dr()
  (SETQ A(SSGET  (LIST (CONS 2 "P*"))))
  (SETQ B(SSLENGTH A))
  (SETQ NUM 0)
  (REPEAT B
    (SETQ C(SSNAME A NUM))
    (SETQ D(ENTGET C))
    (SETQ E(CDR(ASSOC 10 D)))
    (COMMAND "INSERT" "a" E "" "" "")
    (SETQ NUM(+ NUM 1))
  )
  )
(DEFUN C:Dr1()
  (SETQ A(SSGET "x" (LIST (CONS 2 "P*"))))
  (SETQ B(SSLENGTH A))
  (SETQ NUM 0)
  (REPEAT B
    (SETQ C(SSNAME A NUM))
    (SETQ D(ENTGET C))
    (setq ed (subst (cons 2 "SP") (assoc 2 d) d ))
    (entmod ed)
    (SETQ NUM(+ NUM 1))
))
(DEFUN C:Dr2()
  (SETQ A(SSGET "x" (LIST (CONS 2 "DP3"))))
  (SETQ B(SSLENGTH A))
  (SETQ NUM 0)
  (REPEAT B
    (SETQ C(SSNAME A NUM))
    (SETQ D(ENTGET C))
    (setq ed (subst (cons 2 "DP5") (assoc 2 d) d ))
    (entmod ed)
    (SETQ NUM(+ NUM 1))
))
(DEFUN C:Dr3()
  (SETQ A(SSGET "x" (LIST (CONS 2 "DP4"))))
  (SETQ B(SSLENGTH A))
  (SETQ NUM 0)
  (REPEAT B
    (SETQ C(SSNAME A NUM))
    (SETQ D(ENTGET C))
    (setq ed (subst (cons 2 "DP5") (assoc 2 d) d ))
    (entmod ed)
    (SETQ NUM(+ NUM 1))
))
(defun c:8()
  (princ "To \nEnter length if it is not there")(princ)
  (setq pl(Entsel "Pick Cable : "))
  (setq a(car(entsel "Pick Cable-Text to Change: ")))
  (COMMAND "LENGTHEN" pl "")
  (SETQ VL1(GETVAR "PERIMETER"))
  (setq vl(rtos vl1 2 0))
  (setq r(entget a))
  (setq s(cdr(assoc 1 r)))
  (setq b(strlen s))
  (setq f 1)
  (repeat b
    (setq c(substr s f 1))
    (if (= c "/")
      (setq st f)
      )
    (setq f(+ f 1))
  )
  (setq st2(abs(- 1 st)))
  (setq fv(substr s 1 st2))
  (setq fv1(substr s st ))
  (setq ft(strcat fv "/" vl))
  (setq ed (subst (cons 1 ft)(assoc 1 r) r))
  (entmod ed)
)
(defun c:7()
  (setq pl(Entsel "Pick Cable : "))
  (setq a(car(entsel "Pick Cable-Text to Change: ")))
  (setq a1(cdr(assoc 62(entget (car pl)))))
  (COND  ((= a1 4)(SETQ cl "10"))
	 ((= a1 11)(SETQ cl "20"))
	 ((= a1 32)(SETQ cl "50"))
	 ((= a1 200)(SETQ cl "100"))
	 ((= a1 5)(SETQ cl "200"))
	 ((= a1 149)(SETQ cl "400"))
 	 ((= a1 30)(SETQ cl "800"))
	 ((= a1 145)(SETQ cl "1200"))
	 ((= a1 224)(SETQ cl "1600"))
  )
  (COMMAND "LENGTHEN" pl "")
  (SETQ VL1(GETVAR "PERIMETER"))
  (setq vl(rtos vl1 2 0))
  (setq r(entget a))
  (setq s(cdr(assoc 1 r)))
  (setq b(strlen s))
  (setq f 1)
  (repeat b
    (setq c(substr s f 1))
    (if (= c "/")
      (setq st f)
      )
    (setq f(+ f 1))
  )
  (setq st2(abs(- 1 st)))
  (setq fv(substr s 1 st2))
  (setq fv1(substr s st ))
  (setq ft(strcat cl "/" vl))
  (setq ed (subst (cons 1 ft)(assoc 1 r) r))
  (entmod ed)
)
(defun c:aa()
  (setq a(ssget))
  (command "change" a "" "p" "la" "Alone" "" )
)
(defun c:wb()
  (setq a(ssget))
  (command "change" a "" "p" "la" "With-Bescom" "" )
)
(defun c:q()
  (command "layer" "off" "*" "" "on" "Alone,With-Bescom" "")
)
(defun c:w()
  (command "layer" "off" "Alone,With-Bescom" "")
)
(defun c:rtt()
  (setq c (getint "Enter Angle: "))
  (setq d(car(entsel "Pick Text to Align: ")))
  (while (= d nil)
      (setq d(car(entsel "Pick Text to Align: ")))
  )
  (setq e(entget d))
  (setq f(cdr(assoc 50 e)))
  (setq ed(subst (cons 50 c) (assoc 50 e) e))
  (entmod ed)
  (setvar "osmode" os)
)
(defun c:bt()
  (command "MAPTRIM" "s" pause "n" "n" "o" "y" "n" "i" "y" )
  )
(defun c:mm()
  (setvar "filedia" 0)
  (setq os(getvar "osmode"))
  (setvar "osmode" 1)
  (command "zoom" pause pause "")
  (setq a(getvar "dwgname"))
  (setq b(substr a 1 5))
  (setq c(strcat "c/img/" b))
  (command "bmpout" c "box" pause pause "")
  (setvar "osmode" os)
  )

(defun c:ha()
  (repeat 80
        (setq a(getstring  "Enter no :"))
   	(setq b(strcase a))
  	(setq c(ssget "x"(list (cons 8 "Text")(cons 1 b))))
  	(setq d(ssname c 0))
  	(SETQ e(ENTGET d))
  	(SETQ ip(CDR(ASSOC 10 e)))
  	(command "circle" ip "10")
    )
  )
