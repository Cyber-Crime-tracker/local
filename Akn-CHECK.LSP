(DEFUN C:JCHK()
  (SETQ A(SSGET "X"(LIST (CONS 8 "JOINT_TXT")(CONS 1 "J*"))))
  (SETQ B(SSLENGTH A))
  (SETQ NUM 0)
  (SETQ L NIL)
  (REPEAT B
    (SETQ C(SSNAME A NUM))
    (SETQ D(CDR(ASSOC 1(ENTGET C))))
    (SETQ LL(APPEND L (LIST D)))
    (SETQ L LL)
    (SETQ NUM(+ 1 NUM))
  )
  (SETQ FL(ACAD_STRLSORT LL))
  (SETQ NUM1 0)
  (SETQ NUM2 1)
  (REPEAT B
    (SETQ LS(NTH NUM1 FL))
    (SETQ LF(NTH NUM2 FL))
    (SETQ PT(STRCAT "HELLO Mr/Mrs Please check this Joint Number" LS "=" LF))
    (SETQ NUM1(+ 1 NUM1))
    (SETQ NUM2(+ 1 NUM2))
    (IF (= LS LF)(ALERT PT))
))
(DEFUN C:Sdl()
  (setq ar(getstring "Enter Area Abr: "))
  (setq ft(strcase(strcat ar "*")))
  (SETQ A(SSGET "x"(LIST (CONS 8 "text")(CONS 1 ft))))
  (SETQ B(SSLENGTH A))
  (SETQ NUM 0)
  (SETQ L nil)
  (setq l1 nil)
  (REPEAT B
    (SETQ C(SSNAME A NUM))
    (SETQ D(CDR(ASSOC 1(ENTGET C))))
    (setq stl(strlen d))
    (if (= stl 9)
      (SETQ LL(APPEND L (LIST D)))
      (SETQ LL1(APPEND L1 (LIST D)))
    )
    (SETQ L LL)
    (setq l1 ll1)
    (SETQ NUM(+ 1 NUM))
  )
  (SETQ FL(ACAD_STRLSORT LL))
  (SETQ FL1(ACAD_STRLSORT LL1))
  (setq fla(append '(list of SPs) FL1))
  (setq fla1(append '(list of dPs) FL))
  (princ FLA)(princ)
  (princ FLA1)(princ)
  (SETQ LL NIL)
  (SETQ LL1 NIL)
)
(DEFUN C:NCHK()
  (SETQ AR(strcase(STRCAT (GETSTRING "ENTER AREA NAME:") "*")))
  (SETQ A(SSGET "X"(LIST (CONS 8 "TEXT")(CONS 1 AR))))
  (SETQ B(SSLENGTH A))
  (SETQ NUM 0)
  (SETQ L NIL)
  (REPEAT B
    (SETQ C(SSNAME A NUM))
    (SETQ D(CDR(ASSOC 1(ENTGET C))))
    (SETQ LL(APPEND L (LIST D)))
    (SETQ L LL)
    (SETQ NUM(+ 1 NUM))
  )
  (SETQ FL(ACAD_STRLSORT LL))
  (SETQ NUM1 0)
  (SETQ NUM2 1)
  (REPEAT B
    (SETQ LS(NTH NUM1 FL))
    (SETQ LF(NTH NUM2 FL))
    (SETQ PT(STRCAT "HELLO Mr/Mrs Please check this Joint Number" LS "=" LF))
    (SETQ NUM1(+ 1 NUM1))
    (SETQ NUM2(+ 1 NUM2))
    (IF (= LS LF)(ALERT PT))
  )
)
(DEFUN C:NCHK1()
  (SETQ AR(strcase(GETSTRING "ENTER AREA NAME:")))
  (setq b(Getint "Enter number of Pillars: "))
  (SETQ AR1(STRCAT AR "*"))
  (SETQ A(SSGET "X"(LIST (CONS 8 "TEXT")(CONS 1 AR1))))
  (SETQ NUM 0)
  (SETQ PN 01)
  (REPEAT B
    (SETQ NUM1(RTOS PN 2 0))
    (SETQ NLEN(STRLEN NUM1))
    (IF (= NLEN 1)
      (SETQ NN(STRCAT "0" NUM1))
      (SETQ NN NUM1)
    )
    (SETQ PN1(STRCAT AR NN "00"))
    (SETQ A1(SSGET "X"(LIST (CONS 8 "TEXT")(CONS 1 PN1))))
    (SETQ PN (+ PN 1))
    (IF (/= a1 nil)
      (alert (STRCAT "THERE ARE/IS" " " (RTOS (SSLENGTH A1) 2 0) " "
		      "NUMBER OF " PN1 " IN THIS DWG" ))
      (alert (strcat "No Probs in " ar nn " Pillar"))
    )
  )
)
