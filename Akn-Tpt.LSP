(DEFUN C:BOQF()
  (command "line" "0,0" "0,0" "")
  (setq sri(entlast))
  (command "lengthen" sri "")
  (command "erase" sri "")
  (setq a(ssget (list (cons 0 "lwpolyline"))))
  (setq sl(sslength a))
  (setq num 0)boqf
  (setq la 0)
  (setq lb 0)
  (setq lc 0)
  (setq ld 0)
  (setq le 0)
  (setq lf 0)
  (setq lg 0)
  (setq lh 0)
  (setq li 0)
  (setq la1 0)
  (setq lb1 0)
  (setq lc1 0)
  (setq ld1 0)
  (setq le1 0)
  (setq lf1 0)
  (setq lg1 0)
  (setq lh1 0)
  (setq li1 0)
  (repeat sl
    (setq an(ssname a num))
    (COMMAND "LENGTHEN" an "")
    (SETQ len(GETVAR "PERIMETER"))
    (setq b(cdr(assoc 62 (entget an))))
    (if(= b 30)(setq la1(+ la len)))
    (if(= b 200)(setq lb1(+ lb len)))
    (if(= b 32)(setq lc1(+ lc len)))
    (setq la la1)
    (setq lb lb1)
    (setq lc lc1)
    (setq num(+ num 1))
    )
  (setq fla(strcat "\nTotal Length of 96 Fiber Cable =" " "
		   (rtos la1 2 2)))
  (setq flb(strcat "\nTotal Length of 48 Fiber Cable =" " "
		   (rtos lb1 2 2)))
  (setq flc(strcat "\nTotal Length of 24 Fiber Cable =" " "
		   (rtos lc1 2 2)))
  (princ fla)(princ)
  (princ flb)(princ)
  (princ flc)(princ)
  )
(DEFUN C:3()
  (command "layer" "S" "0" "off" "BLDG_TXT,DLC,EXG_TXT,Landmarks,MAN HOLE,MPIL_TXT,other,OTHER_TEXT,RD_Old,RD_RSI,RD_Tricad,RD_TXT,RSU,Tpt_Rings,Bldg" "")
)
