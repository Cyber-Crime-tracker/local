Princ " Lisp for Reguraly Used Commands by Narahari.A.K"
(defun c:`() (command "'layer" "on" "*" ""))(defun c:1() (command "'layer" "off" "*" "" ""))
(defun c:cr() (command "circle" ))
(defun c:0() (setvar "clayer" "0"))
(DEFUN C:C()(COMMAND "COPY"))
(DEFUN C:0()(SETVAR "CLAYER" "0"))
(defun c:On()
  (setq a(getstring "Enter names of layers to be switched on: "))
  (command "layer" "on" a "")
)
(defun c:Off()
  (setq a(getstring "Enter names of layers to be switched off: "))
  (command "'layer" "off" a "")
)
(defun c:of()
  (setq a(car(entsel "Pick entity to be off: ")))
  (setq b(cdr(assoc 8(entget a))))
  (command "'layer" "off" b "")
)
(defun c:see()
  (setq a(car(entsel "pick entity: ")))
  (setq b(cdr(assoc 8(entget a))))
  (command "'layer" "s" b "off" "*" "" "")
)
(defun c:ent()
  (setq a(car(entsel "Pick entity for prop: ")))
  (setq b(entget a))
)
(DEFUN C:BF()
  (SETQ A(ENTSEL "PICK ENTITY TO BREAK: "))
  (SETQ B(GETPOINT "PICK POINT OF BREAK: "))
  (COMMAND "BREAK" A "F" B B )
)
(defun c:tt()
  (setq nt(car(entsel "Pick text: ")))
  (SETQ ntp(cdr(assoc 1(ENTGET  nt))))
  (setq num 01)
  (repeat 10
  (setq ot(car(entsel "Pick changing text: ")))
  (SETQ otp(ENTGET  ot))
  (setq ed (subst (cons 1 ntp) (assoc 1 otp) otp ))
  (entmod ed)
)
)
(defun c:cl()
  (setq a(ssget))
  (setq la(getstring "Enter layer name: "))
  (command "change" a "" "p" "la" la "")
)
(defun c:cc()
  (setq a(ssget))
  (setq la(getstring "Enter colour: "))
  (command "change" a "" "p" "c" la "")
)
(defun c:cu()
  (setq a(ssget))
  (setq num 0)
  (setq le(sslength a))
  (repeat le
  (setq aa(ssname a num))
  (setq a1(entget aa))s
  (setq b(cdr(assoc 1 a1)))
  (setq c(strcase b))
  (setq ed (subst (cons 1 c) (assoc 1 a1) a1 ))
  (entmod ed)
  (setq num (+ num 1))
  )
)
(defun c:chl()
  (setq a(ssget))
  (setq num 0)
  (setq le(sslength a))
  (repeat le
  (setq aa(ssname a num))
  (setq a1(entget aa))s
  (setq b(cdr(assoc 1 a1)))
  (setq c(strcase b t))
  (setq ed (subst (cons 1 c) (assoc 1 a1) a1 ))
  (entmod ed)
  (setq num (+ num 1))
  )
)
(DEFUN C:FR()
  (setq a(car(entsel "Pick entity to be FREEZE: ")))
  (setq b(cdr(assoc 8(entget a))))
  (command "layer" "F" b "")
)
(DEFUN C:TH()
  (setq a(getstring "Enter names of layers to be thawed: "))
  (command "layer" "t" a "")
)
(DEFUN C:LL()
  (LOAD "C:/akn/LISP/AKN.LSP")
  (LOAD "C:/akn/LISP/AKN-btnl.LSP")
)
(defun c:rt()
  (setq os(getvar "osmode"))
  (setvar "osmode" 512)
  (setq a(getpoint "Pick Nearby End point: "))
  (setq b(getpoint a "Pick Nearby End point: "))
  (setq c(angle a b))
  (setq d(car(entsel "Pick Text to Align: ")))
  (while (= d nil)
      (setq d(car(entsel "Pick Text to Align: ")))
  )
  (setq e(entget d))
  (setq f(cdr(assoc 50 e)))
  (setq ed(subst (cons 50 c) (assoc 50 e) e))
  (entmod ed)
  (setvar "osmode" os)
)

(defun c:rt1()
  (setq os(getvar "osmode"))
  (setvar "osmode" 512)
  (setq a(getpoint "Pick Nearby End point: "))
  (setq b(getpoint a "Pick Nearby End point: "))
  (setq c(angle a b))
  (setq ent(ssget))
  (setq sl(sslength ent))
  (setq num 0)
  (repeat sl
    (setq d(ssname ent num))
    (setq e(entget d))
    (setq ed(subst (cons 50 c) (assoc 50 e) e))
    (entmod ed)
    (setq num(+ num 1))
  )
    (setvar "osmode" os)
)
(DEFUN C:SET()
  (SETQ A(GETSTRING "ENTER LAYER TO SET CURRENT: "))
  (COMMAND "'LAYER" "S" A "")
)
(defun c:rt0()
  (setq a(ssget))
  (setq num 0)
  (setq le(sslength a))
  (setq c 0)
  (repeat le
  (setq d(ssname A NUM))
  (setq e(entget d))
  (setq f(cdr(assoc 50 e)))
  (setq ed(subst (cons 50 c) (assoc 50 e) e))
  (entmod ed)
  (SETQ num(+ num 1))
  )
)
(DEFUN C:SL()
  (SETQ A(CDR(ASSOC 1(ENTGET(CAR(ENTSEL "PICK TEXT: "))))))
  (SETQ B(STRLEN A))
  (PRINC B)(PRINC)
)
(Defun c:nxt()
   (setvar "cmdecho" 0)
   (setq ln (cdr (assoc 2 (tblnext "LAYER" t))))
   (while (/= nil (setq ln (cdr (assoc 2 (tblnext "LAYER")))))
     (if (not (member ln laylst))
         (setq laylst (append laylst (list ln)))
     )
   )
   (Setq ln (car laylst))
   (command "layer" "t" ln "u" ln "on" ln "s" ln "off" "*" "" "")
   (setq laylst (cdr laylst))
(princ)
)
(defun c:pa()
  (COMMAND "LAYER" "S" "0" "")
  (command "purge" "a" "*" "n")
  (command "purge" "a" "*" "n")
  (command "zoom" "e")
  (command "qsave")
)
(defun c:pac()
  (COMMAND "LAYER" "S" "0" "on" "*" "")
  (command "purge" "a" "*" "n")
  (command "purge" "a" "*" "n")
  (command "zoom" "e")
  (command "qsave")
  (command "close")
)
(DEFUN C:LAY()
  (COMMAND "SCRIPT" "C:/akn/LISP/LAYER.SCR")
)
(defun c:ror()
  (princ "To rotate object with ref")
  (setq a(ssget))
  (setq b(getpoint "pick Basepoint: "))
  (command "rotate" a "" b "r" b pause pause)
)
(defun c:scr()
  (princ "To rotate object with ref")
  (setq a(ssget))
  (setq b(getpoint "pick Basepoint: "))
  (command "scale" a "" b "r" b pause pause)
)
(DEFUN C:FLT()
  (SETQ A(GETSTRING "Enter String to Find: "))
  (setq b(ssget "x"(list (cons 1 a))))
  (setq c(ssname b 0))
  (setq d(entget c))
  (setq e(cdr(assoc 10 d)))
  (SETQ F(CDR(ASSOC 40 D)))
  (SETQ G(+ F 10))
  (COMMAND "ZOOM" "C" E G)
)
(DEFUN C:CT()
  (princ "To change Text" )(princ)
  (SETQ OT(GETSTRING "ENTER TEXT to find: "))
  (SETQ NT(GETSTRING "ENTER NEW TEXT: "))
  (SETQ A(SSGET "X"(LIST (CONS 1 ot))))
  (SETQ B(SSLENGTH A))
  (SETQ NUM 0)
  (REPEAT B
    (SETQ ON(SSNAME A NUM))
    (SETQ ON1(ENTGET ON))
    (setq ed (subst (cons 1 nt) (assoc 1 on1) on1 ))
    (entmod ed)
    (setq num (+ num 1))
  )
)
(Defun c:rev ()
  (setq a(car(entsel "Pick Text TO reverse: ")))
  (setq r(entget a))
  (setq s(cdr(assoc 1 r)))
  (setq b(strlen s))
  (Setq z b)
  (setq e "")
  (repeat b
    (setq c (substr s z 1))
    (setq z (- z 1))
    (Setq e (strcat e c))
  )
  (setq ed (subst (cons 1 e) (assoc 1 r) r))
  (entmod ed)
)
(Defun c:PLW ()
  (Setvar "cmddia" 0)

; object selection method
  (initget 1 "L S G")
  (setq osm (getkword "select object by <Layer/Selection/Global>:"))
   (cond
    ((= osm "L") (while (or (not (tblsearch "LAYER" 
                        (setq layn (getstring "\nEnter Layer Name:"))))
                        (= (cdr (assoc 70 (tblsearch "LAYER" layn))) 4))
                        (princ "\nSpecified Layer doesn't exist or its Locked."))
                        (Setq sels (ssget "X" (list (cons 8 layn)))))
    ((= osm "S") (while (= nil (setq sels (ssget)))))
    ((= osm "G") (setq sels (ssget "X")))
   )

; Main Program
 (if sels
  (progn 
   (setq selslen (sslength sels)
	   loopc 0
          grpcnt 0
            wdth (getdist "\nEnter Width for Selected Entities:"))
    (if (or (= osm "G") (= osm "S"))
                 (Alert "\nObjects on Locked Layers will be Ignored."))
    (repeat selslen
     (princ (strcat "\rAssigned Width to " (itoa (1+ loopc)) " of "
                    (itoa selslen) " selected Elements, Wait....."))
       (setq ennam (ssname sels loopc)
           enlst (entget ennam)
           layer (cdr (assoc 8 enlst))
           entty (cdr (assoc 0 enlst))
           loopc (1+ loopc)
           cflag (cdr (assoc 70 elist)))

; Assigning Width based on Entity Type
      (if (and (or (= entty "LINE") (= entty "ARC"))
          (/= (cdr (assoc 70 (tblsearch "LAYER" layer))) 4))
       (command "pedit" ennam "Y" "w" wdth "X")
      )
      (if (and (or (= entty "POLYLINE") (= entty "LWPOLYLINE"))
          (/= (cdr (assoc 70 (tblsearch "LAYER" layer))) 4))
       (command "pedit" ennam "w" wdth "X")
      )
      (if (and (= entty "CIRCLE")
          (/= (cdr (assoc 70 (tblsearch "LAYER" layer))) 4))
       (progn
        (setq rad (cdr (assoc 40 enlst))
              cen (cdr (assoc 10 enlst))
              brp (polar cen (* 0.5 pi) rad))
        (command "break" ennam cen brp)
        (command "pedit" ennam "Y" "c" "W" wdth "X")
       )
      )
    )
  )  
 )
 (prompt "Done.")
 (princ)
)
(Defun c:cul()
  (setq a(ssget))
  (setq num 0)
  (setq le(sslength a))
  (repeat le
  (setq aa(ssname a num))
  (setq a1(entget aa))
  (setq b(cdr(assoc 1 a1)))
  (SETQ D(SUBSTR B 1 1))
  (SETQ DF(STRCASE D))
  (SETQ E(SUBSTR B 2 ))
  (SETQ EF(STRCASE E T))
  (SETQ FT(STRCAT DF EF))
  (SETQ ED(SUBST (CONS 1 FT)(ASSOC 1 A1) A1))
  (ENTMOD ED)
    (SETQ NUM (+ NUM 1))
    )
  )
(defun c:PED()
     (prompt "\nselect objects to edit the width to 0.0")
       (setq pset (ssget)
       plen (sslength pset)
       ctr 0 
       )
       (repeat plen
       (setq pname (ssname pset ctr))
       (command "pedit"pname"w" "0" "")
       (setq ctr (1+ ctr))
       )
       (princ)
)
(defun c:PJ()
     (prompt "\nselect objects to edit the JOIN to SELECT")
       (setq pset (ssget)
       plen (sslength pset)
       ctr 0 
       )
       (repeat plen
       (setq pname (ssname pset ctr))
       (command "pedit"pname"J")
       (setq ctr (1+ ctr))
       )
       (princ)
)
(defun c:str()
  (COMMAND "SCRIPT" "C:/akn/LISP/LAYER.SCR")
  (COMMAND "INSERT" "c:/akn/str.dwg" "0,0" "" "" "")
  (command "zoom" "e")
  (Setq a(Entlast))
  (Command "Explode" a)
  (command "zoom" "p")
)
(defun cost()
  (command "ucsicon" "off")
  (load "c:/akn/lisp/Akn.lsp")
  (load "c:/akn/lisp/Akn-BTNL.lsp")
  (command "pickbox" "4")
  (command "aperture" "6")
  (command "cursorsize" "5")
  )
(defun c:ff()
  (command "fillet" "r" "0" pause pause))
